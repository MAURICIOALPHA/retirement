;;Alpha_GPCNC Lisp
(setvar "cmdecho" 0)
(defun DisplayBitmap ( key lst / i j s x y )
	(setq s (fix (sqrt (length lst))))
	(repeat 
		(setq i s)
		(setq j 1)
		(repeat s
			(setq x (cons j x) y (cons i y) j (1+ j))
		)
		(setq i (1- i))
	)
	(start_image key)
	(fill_image 0 0 (dimx_tile key) (dimy_tile key) -15)
	(mapcar 'vector_image x y x y lst)
	(end_image)
)
(defun listaentidades()
	(setq indice (+ 1 indice))
	(setq entidade (ssname entidades indice))
	(setq definicao (entget entidade))
	(setq tipo (cdr (assoc 0 definicao)))
)
(setq test_blue
    '(
252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 252 252 252 252 252 252 252 252 252 12118000 7653337 3649225 4174025 4502476 4634058 5093582 5093839 5093839 5094095 5093582 5027790 5027535 4764879 4501966 4041932 3581641 8045529 12509418 252 252 252 252 252 252 252 252 252 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 252 252 252 252 252 10935011 4699078 4371398 5159887 5291470 5357008 5422798 5423051 5423307 5423306 5423057 5423062 5357518 5357264 5357265 5357009 5291217 5290960 5225168 5225166 5224652 5158605 5092557 5026512 4172233 4106184 8964057 252 252 252 252 252 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 16711679 6799319 4765647 5357010 5357271 5423322 5423834 5489610 5489613 5555408 5489872 5555409 5555665 5555665 5621201 5621455 5555658 5555674 5489891 5555430 5555172 5489379 5423842 5423331 5357539 5357282 5291235 5290979 5290723 5158877 5092839 5092575 4960739 4960229 4500187 4104641 13428717 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 14807798 4305354 5224914 5291473 5423051 5423309 5489362 5489866 5555662 5621456 5621715 5621455 5621713 5621713 5621711 5621713 5687524 5687525 5621988 5621731 5555940 5555939 5555684 5555427 5489891 5555171 5489379 5489124 5423074 5357539 5357027 5291235 5225183 5224669 5092829 5092319 5026273 4894176 4762077 4104664 10538464 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 8768482 4371401 5290959 5422792 5357768 5423561 5555149 5555658 5621453 5556175 5621966 5687248 5621968 5688019 5753560 5753572 5753572 5753571 5687780 5688036 5622499 5622245 5622244 5621987 5621987 5556195 5556196 5621475 5490148 5555428 5423844 5489122 5357794 5357027 5356770 5225441 5159394 5158881 5158367 5092319 4960475 4894178 4761818 4170195 3905991 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 11327970 4173510 5159119 5357000 5357771 5489099 5555403 5555404 5556172 5687502 5622221 5622223 5753551 5688271 5688273 5688292 5753826 5819618 5819874 5819877 5819876 5819620 5753828 5754083 5688549 5753573 5753572 5753317 5622245 5687781 5687525 5556196 5621220 5555684 5555428 5489634 5489124 5357796 5422818 5356768 5225441 5159137 5093088 5027038 5092321 4960222 4893918 4761819 4629718 4103371 5875146 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 4435135 5224908 5290962 5357255 5489100 5489357 5489869 5621709 5621710 5687758 5688014 5753807 5688526 5754071 5819876 5819874 5819874 5819874 5819875 5754595 5754339 5820139 5754595 5819875 5819875 5819876 5754085 5688549 5753829 5753829 5753316 5622245 5687269 5621731 5621477 5621477 5489890 5489378 5489114 5423322 5422801 5357009 5225425 5224916 5158615 5158359 5026522 4960478 4828378 4761820 4695514 4563411 2920130 14675443 252 252 252 252 252 252 252 252 252 252 252 252 252 252 252 252 252 252 252 252 252 252 252 252 252 252 252 252 252 252 
252 252 252 252 252 252 252 252 252 252 252 252 252 252 252 252 252 252 252 252 252 252 252 252 252 252 252 252 252 6010311 5027274 5224908 5356999 5423306 5489099 5555151 5555662 5555918 5687502 5622222 5688013 5688271 5754061 5819875 5820128 5754338 5754338 5820130 5820129 5820385 5885922 5885922 5885922 5885931 5820130 5754339 5819875 5819620 5819876 5753828 5688549 5753829 5753572 5622237 5687765 5555921 5621457 5621457 5555408 5423825 5488849 5357520 5357264 5357008 5290703 5159119 5158863 5027023 5026511 4894669 4893897 4762058 4696017 4497626 4365518 2590648 252 252 252 252 252 252 252 252 252 252 252 252 252 252 252 252 252 252 252 252 252 252 252 252 252 252 252 252 252 
252 252 252 252 252 252 252 252 252 252 252 252 252 252 252 252 252 252 252 252 252 252 252 252 252 252 252 6600905 5026756 5224906 5290955 5357258 5489104 5489612 5555661 5556174 5687504 5622223 5753551 5688271 5754065 5819873 5820129 5754336 5885922 5885665 5886176 5885921 5886177 5886178 5886177 5886178 5886177 5886177 5885921 5885922 5885922 5820131 5820124 5819600 5819857 5753810 5753554 5753297 5622226 5687250 5556177 5621457 5555409 5555153 5489616 5488850 5357777 5357266 5356754 5225170 5159378 5093074 5092818 5026512 4894670 4828619 4762313 4695752 4629442 4497345 4299208 3443641 252 252 252 252 252 252 252 252 252 252 252 252 252 252 252 252 252 252 252 252 252 252 252 252 252 252 252 
252 252 252 252 252 252 252 252 252 252 252 252 252 252 252 252 252 252 252 252 252 252 252 252 252 252 6206405 5092553 5224649 5291207 5423051 5423307 5555147 5555660 5556173 5687503 5622223 5753808 5754064 5819876 5819874 5754337 5820128 5885666 5885922 5886178 5885922 5820897 5820898 5820642 5820642 5885922 5885922 5885922 5886177 5885918 5885389 5885647 5754064 5819855 5819856 5819856 5754065 5753552 5753296 5687762 5687250 5555922 5621458 5489874 5555410 5423826 5489105 5423059 5291732 5290965 5290708 5224401 5092818 5026768 4960718 4894413 4828363 4762056 4630215 4563650 4431294 4299196 2260911 252 252 252 252 252 252 252 252 252 252 252 252 252 252 252 252 252 252 252 252 252 252 252 252 252 252 
252 252 252 252 252 252 252 252 252 252 252 252 252 252 252 252 252 252 252 252 252 252 252 252 252 3580857 5026757 5159117 5291208 5422795 5488844 5489363 5621198 5621709 5687501 5622223 5753806 5688527 5819873 5820130 5754338 5885922 5885664 5886176 5886178 5885920 5886433 5951970 5951970 5951969 5951970 5886433 5886433 5885653 5885390 5885648 5885653 5885134 5885391 5819342 5819598 5819599 5688528 5753551 5753809 5622480 5687762 5687504 5621458 5621459 5490130 5424083 5489363 5357521 5357011 5357012 5225684 5159379 5158610 5158096 5092303 5025998 4959950 4762571 4696265 4629960 4563134 4365504 4232890 3706547 12112866 252 252 252 252 252 252 252 252 252 252 252 252 252 252 252 252 252 252 252 252 252 252 252 252 
252 252 252 252 252 252 252 252 252 252 252 252 252 252 252 252 252 252 252 252 252 252 252 6666186 5092044 5158348 5159122 5356747 5423052 5423821 5555406 5621200 5555919 5687247 5622222 5753554 5688546 5819873 5820127 5754336 5885921 5886176 5886177 5885919 5820896 5886433 5951969 5951967 5951713 5952225 5951187 5950670 5950672 5819856 5885391 5885390 5885390 5885134 5885394 5754061 5819341 5819341 5819598 5688527 5753552 5753295 5687505 5687248 5621712 5621458 5490131 5554898 5489361 5489106 5423057 5291217 5356497 5290450 5224403 5092819 5027025 4960721 5025746 4828625 4827854 4761548 4563911 4563137 4430781 4299194 4166585 1996961 252 252 252 252 252 252 252 252 252 252 252 252 252 252 252 252 252 252 252 252 252 252 252 
252 252 252 252 252 252 252 252 252 252 252 252 252 252 252 252 252 252 252 252 252 252 2726586 4960201 5158346 5224658 5225417 5357259 5423308 5555150 5490129 5621199 5687249 5621969 5753552 5754082 5753824 5819873 5819872 5820383 5885664 5886176 5885921 5886431 5951968 5951968 5951967 5951968 5951968 5950668 5950926 5950926 5950671 5819599 5885135 5885135 5885391 5885391 5885133 5885390 5819599 5819343 5819086 5753549 5753807 5753552 5687503 5687248 5621714 5621458 5490130 5554898 5423825 5488850 5422802 5291729 5357011 5290962 5159123 5093075 5027283 5092308 5026004 4894161 4828113 4762061 4629961 4629189 4497087 4299453 4298681 4100532 3179698 16777214 252 252 252 252 252 252 252 252 252 252 252 252 252 252 252 252 252 252 252 252 252 
252 252 252 252 252 252 252 252 252 252 252 252 252 252 252 252 252 252 252 252 252 3711678 4894412 5092307 5224657 5290699 5356748 5357516 5423820 5555151 5621209 5556175 5687760 5753310 5753825 5688291 5819873 5819616 5754593 5885921 5885664 5886176 5885919 5820896 5951967 5951967 5951969 5950412 5950669 5950671 5950414 5950413 5950669 5885134 5885135 5885135 5884879 5885135 5885391 5819865 5819854 5819599 5819598 5754061 5753806 5753552 5687504 5687248 5621712 5621458 5489874 5555409 5424081 5488848 5423314 5291475 5357011 5290963 5290707 5224661 5158101 5092565 4960981 4960210 4828624 4762320 4696011 4629705 4497346 4365504 4364990 4166581 3968687 3705015 252 252 252 252 252 252 252 252 252 252 252 252 252 252 252 252 252 252 252 252 252 
252 252 252 252 252 252 252 252 252 252 252 252 252 252 252 252 252 252 252 13953260 4631495 5026248 5027016 5158857 5225422 5356751 5422799 5489358 5554895 5555407 5621455 5687503 5556707 5229543 5426148 5819874 5819618 5820130 5885920 7325909 7129302 5297124 5558754 5820896 5951191 5950156 5950157 5950670 5950669 5950157 5950413 5950414 5950414 5950670 5885133 5885134 5885134 5885135 5885134 5819855 5819857 5819855 5688527 5753551 5753806 5622480 5687760 5687248 5555920 5621199 5489874 5555154 5424082 5488850 5423313 5291474 5357010 5290964 5290710 5224404 5158613 5027031 4960983 4894677 4828883 4828113 4761806 4695756 4563401 4431559 4431042 4298940 4101044 4034487 3836067 4490912 252 252 252 252 252 252 252 252 252 252 252 252 252 252 252 252 252 252 252 
252 252 252 252 252 252 252 252 252 252 252 252 252 252 252 252 252 252 13756395 4696259 3439504 5489629 5093068 5224909 5356749 5357006 5357521 5423825 5555408 5621460 5555919 6278889 12169389 11907503 12496555 5819873 5820130 5820128 5889263 12696506 11645618 11710897 12234669 5754840 5950669 5950670 5950414 5950414 5950669 5950157 5949901 5949901 5950156 5819341 5884878 5884878 5884621 5884621 5753806 5819597 5819343 5819862 5688528 5753551 5753807 5622479 5687759 5687248 5621711 5621456 5490129 5554898 5489105 5488851 5423314 5291474 5357012 5290965 5290710 5224406 5158614 5027030 4960727 4894934 4959957 4893907 4696272 4629968 4629453 4497352 4431301 4298942 4167100 4166069 3902387 3769764 4096412 252 252 252 252 252 252 252 252 252 252 252 252 252 252 252 252 252 252 
252 252 252 252 252 252 252 252 252 252 252 252 252 252 252 252 252 252 4630469 4960464 250 1124654 5224653 5290445 5356750 5423055 5489106 5554898 5555666 5621209 5622248 393216 9 9 9 5623266 5819617 5820129 3438979 12237498 9 9 11710897 5754319 5884877 5950414 5950414 6015949 5884878 5491919 5819085 5819085 5819085 5884365 5884876 5884877 5884876 5818829 5819340 5819086 5819597 5819342 5754062 5753552 5753552 5687503 5687503 5687503 5621457 5621457 5490128 5554897 5489363 5489107 5423060 5291475 5357011 5290965 5290709 5224407 5158615 5026776 5092310 4894934 4959960 4893910 4761812 4696016 4563918 4497610 4497351 4299457 4232894 4166843 4033976 3901873 3703725 252 252 252 252 252 252 252 252 252 252 252 252 252 252 252 252 252 252 
252 252 252 252 252 252 12185852 252 252 252 252 252 252 252 252 252 13690601 4564175 4828378 2513780 4431301 5357018 5555935 5225168 5422544 5423314 5292498 8633026 5097173 5556186 3898498 1381653 9 9 9 11710897 11841968 11907247 12039862 9 9 9 9 10663606 5361617 5623248 5428181 11645618 9 11645618 12823980 5819342 5884877 5884622 5885134 5885134 5819599 5819086 5819085 5819597 5819342 5688525 5753549 5753551 5622481 5687761 5687505 5621457 5621457 5555410 5555154 5424082 5489363 5423316 5423060 5291477 5357013 5290963 5290196 5224662 5158625 5027305 5092327 5026023 4959719 4894183 4827876 4761826 4564189 4498139 4563160 4431053 4233413 4167359 4034742 3902648 3770549 3637421 3964571 252 252 252 252 252 252 252 252 252 252 252 252 252 252 252 252 
252 252 252 252 252 252 252 252 252 252 252 252 252 252 252 13887214 4498123 4696278 5158630 250 5621752 5687541 264717 5356773 5357268 9222079 11776433 11645618 12365742 5491933 983296 986895 11842740 9 9 9 9 11513775 11447982 11513775 11579568 9 9 9 11907248 12300206 9868436 9 9 9 12300207 5688527 5885134 5885135 5885391 5820111 5820112 5819855 5819343 5819343 5688526 5753551 5753552 5688022 5621968 5687250 5555922 5621714 5621202 5490129 5555410 5423571 5488850 5357522 5423061 5291741 5357028 5290982 5290213 5224677 5158629 5026791 5092327 4894951 4959974 4893926 4827875 4761825 4563932 4497882 4563160 4431061 4364497 4233165 4166342 4034238 3836593 3703726 3505572 4292253 252 252 252 252 252 252 252 252 252 252 252 252 252 252 252 
252 252 252 252 252 252 252 252 252 252 252 252 252 252 252 4103363 4630226 4762585 4960735 4894425 4695757 4762063 5026777 5357286 4959695 10592673 9 9 9 10661552 13027014 9 9 11447982 9 14606046 16250871 16250871 16316664 16448250 16645629 16316664 15461355 13684944 9 11513775 9 9 9 9 12431792 5819855 5885391 5819855 5820113 5820113 5819857 5819600 5819599 5688527 5753807 5753807 5688015 5622225 5687771 5687505 5621714 5621203 5489874 5555153 5555154 5423578 5488866 5423076 5423075 5422820 5291491 5290725 5290470 5224421 5158629 5027047 5092070 4894950 4959973 4893926 4827875 4761827 4563934 4563419 4563163 4365783 4365009 4298445 4166598 4034500 3967935 3704247 3637415 3439011 252 252 252 252 252 252 252 252 252 252 252 252 252 252 252 
252 252 252 252 252 252 252 252 252 252 252 252 252 252 3052218 4695508 4762072 4828636 4960736 5027042 5092834 5290724 5225182 5357029 1642766 2105376 11776947 9 9 9 9 12434877 14540253 11250603 7237230 5131854 4276545 3815994 3552822 3618615 3881787 4473924 4868682 5395026 9605778 12566463 15856113 14474460 11316396 11579568 11776433 11907505 4903637 5689042 7718087 12300206 8830657 5622995 5754067 5753809 5753553 5688018 5687761 5687505 5687505 5555922 5621201 5621210 5489636 5555426 5554915 5554659 5488866 5488612 5488612 5357284 5422565 5225188 5290468 5224167 5158117 5027045 4960998 4894951 4959975 4893927 4827363 4761826 4695520 4628957 4562907 4365783 4299218 4298959 4101066 4100295 3968451 3835834 3637941 3505838 3175581 252 252 252 252 252 252 252 252 252 252 252 252 252 252 
252 252 252 252 252 252 252 252 252 252 252 252 252 3511491 4563154 4695768 4762330 4894430 4960993 5026787 5093347 5225185 5094358 5489885 1974047 2236962 2105376 9 9 11974326 12763842 10263708 3815994 3815994 4013373 4013373 4079166 4079166 3881787 3881787 3881787 3881787 3881787 3815994 3684408 3487029 4934475 8816262 12566463 16514043 9 9 11841969 10990773 11710897 9 11645618 11907248 5491669 5753299 5622482 5687507 5687251 5687505 5555921 5621478 5621474 5620963 5620707 5489891 5555170 5554915 5554403 5488612 5488611 5488356 5422052 5225190 5290468 5224422 5158375 5026533 4960997 4894439 4828904 4893926 4827620 4761316 4695519 4628958 4563418 4365783 4299731 4233424 4166605 4034762 4033989 3836093 3769271 3571892 3373224 2518165 252 252 252 252 252 252 252 252 252 252 252 252 252 
252 252 252 252 252 252 252 252 252 252 252 252 8699345 4431817 4563659 4696280 4828380 4960222 4960739 5027300 5093349 9024966 12431533 10725803 1052688 1118481 12171705 9 11908533 9868950 5789784 3618615 4079166 4079166 4013373 4079166 4144445 3814195 3748659 3881273 3881787 3881787 3815994 3881787 3750201 3750201 3684408 3487029 4737096 6381921 16053492 14211288 11447982 9 9 9 9 11710897 6146260 5622231 5687509 5687507 5687513 5555941 5621474 5621473 5621485 5620963 5620962 5620450 5555172 5489380 5554404 5554148 5554148 5488356 5422309 5356260 5289958 5224421 5158375 5026792 4960484 4959966 4894426 4893912 4696534 4761558 4563924 4563411 4562899 4365774 4299212 4233162 4232135 4034755 4034494 3902135 3704247 3703478 3439537 3307433 1203596 252 252 252 252 252 252 252 252 252 252 252 252 
252 252 252 252 252 252 252 252 252 252 252 252 4496853 4497879 4695253 4827868 4894174 4894432 5092323 5158372 4765673 11645362 9 9 9 9 9 10855845 8092539 3684408 3947580 3484457 3960699 5289932 6414306 6148822 6016722 6017234 6082514 6148306 6476758 7003872 6872800 5749179 3555135 3748916 3684408 3618615 3552822 3421236 3092271 6381921 13027014 12434877 9 9 9 9340034 5687772 5687522 5687270 5687269 5621474 5621474 5620963 5621217 5621218 5621227 5620964 5620451 5620452 5620451 5620195 5554148 5553891 5422308 5356517 5355993 5421782 5421529 5158362 5157850 5092316 5091802 5025242 4762329 4696023 4629975 4564180 4498131 4563154 4431311 4299212 4298954 4232135 4035268 3968960 3836347 3835574 3703731 3570861 3373486 3307177 11848667 252 252 252 252 252 252 252 252 252 252 252 
252 252 252 252 252 252 252 252 252 252 252 3117488 4563151 4629459 4629974 4762590 4828642 4894946 5092324 5158116 3898778 12369084 9 9 9 9 9 7566195 3552822 3945780 4229018 5687782 5884899 6148067 6213858 6213842 6148307 6148051 6344914 6475731 6738131 7000274 6869459 6607058 6214099 6415335 3231568 3618615 3552822 3421236 3289650 3223857 3815994 12566463 15592941 11382189 9 6997978 5687273 5687528 5621735 5556198 5621476 5620964 5555428 5620963 5620962 5686498 5620963 5620709 5620196 5619940 5620197 5554150 5619927 5685463 5685464 5751001 5816281 5684697 5289690 5223643 5223644 5223131 5025498 4827865 4696280 4630230 4563669 4497620 4432083 4430801 4365005 4298955 4232137 4035269 3968962 3836350 3835577 3638197 3571373 3373482 3372710 2846616 252 252 252 252 252 252 252 252 252 252 252 
252 252 252 252 252 252 252 252 252 252 9027534 4431297 4498127 4563922 4630488 4762336 4828899 4894947 5092326 5224940 2234387 2631720 10263708 11908533 9 9 9 10263708 3157549 5887480 5555683 5818596 6147810 6345185 6345441 6279650 6279646 6738129 6606802 6868947 7066067 7262163 7000531 6803922 6476243 6345171 6016723 6018782 2699570 3354157 3289650 3158064 3158064 4144959 8092539 16514043 11579568 11710897 9222856 5556201 5294059 5228523 5490151 5489892 5489893 5620965 5620963 5555427 5685987 5686245 5620198 5620185 5751511 5817305 6014169 6079704 6079960 6079961 6211034 5947611 5421018 5354970 5354971 5288667 5025754 4959449 4696024 4630231 4629460 4497875 4431827 4431055 4364494 4298701 4166856 4035271 3968963 3836352 3836092 3769272 3571120 3439531 3307180 3306910 1334922 252 252 252 252 252 252 252 252 252 252 
252 252 252 252 252 252 252 252 252 10932185 4430783 4497344 4629457 4563924 4761304 4762591 4828641 4894949 5092312 3432044 2763306 3026478 3552822 11513775 9 11974326 13290186 11447982 9 10787479 5870755 6018027 6410979 6608354 6542818 6805218 7527139 7921379 7527133 7328211 7524819 7590098 7328210 7197138 7131602 7000530 6476499 5950933 6016215 5885143 6019302 2758935 3026478 2960685 2763306 3421236 12829635 9 9 11841968 11645618 11645618 12431531 5096426 5555173 5620709 5620710 5555169 5620695 5949143 6014937 6146522 6212057 6277850 6540507 6672091 6737626 6671836 6671579 6342364 5815771 5486557 5486300 5354458 5156826 4959193 4695768 4695511 4628949 4562899 4497107 4430801 4299214 4298703 4101066 4034760 3968964 3836354 3835839 3769786 3506097 3505325 3307434 3307173 3306652 2320532 252 252 252 252 252 252 252 252 252 
252 252 252 252 252 252 252 252 252 3774134 4365506 4431816 4629460 4563926 4761307 4762592 4828386 4894437 5093087 1904394 1776411 2763306 1842204 12040119 11579568 10724259 10066329 15921906 13487565 9 11842740 11182752 6278104 6674659 6805473 7789794 8446177 8577249 8184035 7987684 7918036 7787219 7721427 7655891 7524820 7328211 6803924 6082519 6016471 6016472 5950681 6150380 2895921 2894892 2829099 2763306 6316128 10790052 9 9 9 9 11645618 11841968 5423848 5620699 5555161 5686233 5817816 6277859 6343641 6475227 6541019 6672348 6869212 7000796 7066332 7131866 6934493 6605275 6078685 5749468 5552094 5419740 5157082 5024985 4827096 4629462 4563156 4562899 4497106 4299729 4233167 4167117 4166602 4100296 4033990 3836355 3835581 3769275 3506099 3505328 3438507 3372461 3306662 3175070 252 252 252 252 252 252 252 252 252 
252 252 252 252 252 252 252 252 10340821 4430788 4497089 4563152 4629462 4695512 4761565 4762592 4828643 4960230 5358318 11775918 9 9 9 9 10921638 3947580 3815994 3158064 6447714 16316664 12434620 11579568 9 11908533 10260624 9168874 9822178 9559777 9695218 6987937 7318188 7451573 7843504 6857380 8246487 7852757 7328470 6608086 6148056 6015969 5884647 5884391 5818599 2656926 1913651 9584190 12940661 13269626 13269626 11190978 11126470 11450809 12434877 3160379 5620703 5686236 5620444 5752027 6080730 6475483 6804196 6935771 7001307 7198684 7330013 7526875 7592155 7723485 7328988 7000030 6473438 6275295 6011870 5551580 5419740 5287899 5155801 4761303 4497620 4431828 4496851 4299473 4232912 4232654 4166346 4100297 4033990 3901891 3835840 3638460 3637174 3505330 3438767 3372970 3241128 3306404 2780572 252 252 252 252 252 252 252 252 
252 252 252 252 252 252 252 252 3576750 4365506 4497090 4563411 4629463 4695514 4761564 4762592 4893923 4959717 1977910 12698049 9 9 9 9 10066329 3552822 3289650 3289650 3355443 14555931 15874875 16203840 15282481 15282481 15282481 15348274 14426915 14893120 9083803 11513775 11908533 11776947 11776947 11842740 11050654 7582645 7658718 7001818 6344934 6016229 5755375 4836584 13646145 5 5 5 5 5 5 5 5 5 12584197 4906239 5359846 5620445 5752029 5751773 6277851 6672603 7067099 7330268 7330268 7592669 7723998 7920349 7985628 7985885 7723742 7525853 7196127 6998240 6472159 5748702 5617117 5485277 5287130 4892375 4497364 4431316 4365267 4364497 4298446 4232654 4034764 3968712 3902920 3901635 3835327 3637948 3505847 3439540 3373743 3372715 3241642 3306922 3174818 252 252 252 252 252 252 252 252 
252 252 252 252 252 252 252 7582404 4364729 4497088 4431554 4563412 4629462 4695514 4761566 4827616 4893924 4894176 1445644 7895160 12237498 9 9 9 9145226 3297372 3090469 3552822 250 8454144 5 5 5 5 5 5 5 5 15802400 11645618 9 9 11513775 11447982 9 9 12038577 6731710 6150381 6060930 5 5 5 5 5 5 5 5 5 5 5 5 5 5 5 4512247 5621474 5817566 6409693 6804188 7198941 7657690 7723740 7920606 8116957 8248543 8444894 8707038 8510174 8182749 7918559 7720927 6997983 5880288 5814238 5682397 5353180 5023960 4497108 4431060 4365523 4364497 4167374 4232140 4035019 3968714 3902406 3901892 3704512 3637948 3506105 3439797 3373745 3307693 3372459 3306666 3175334 1466258 252 252 252 252 252 252 252 
252 252 252 252 252 252 16054778 4364726 4430791 4497090 4431812 4563412 4628951 4563932 4630495 4827605 4762333 5094387 2960685 3421236 3552822 3092271 11842740 9 9209218 5292527 5619944 250 250 250 8323072 5 5 5 5 5 5 5 5 14953773 8816262 3158064 2960685 2631720 9 13290186 9 11908533 3230282 5 5 5 5 5 5 5 5 5 5 5 5 5 5 5 5 5 5 5 6216169 7067103 7461598 8051938 8313308 8510687 8707039 8969696 9101025 9428191 9559006 9297118 9035232 8575200 7786463 6602977 6077409 5945567 5550300 5221082 4760022 4431058 4430801 4233168 4166862 4100813 4100299 4033995 3967689 3770307 3769537 3703230 3571383 3505076 3373744 3372974 3372716 3241128 3241124 3240613 4883110 252 252 252 252 252 252 
252 252 252 252 252 252 2590887 4364985 4431043 4497091 4497094 4563413 4497880 4563932 4695520 4696277 4762325 5159415 3421236 3487029 3618615 3750201 7237230 9 9867921 5161714 5619686 2379612 250 250 250 5 5 5 5 5 5 5 5 5 3293248 3947580 3881787 3750201 3487029 2039583 9 250 5 5 5 5 5 5 5 5 5 5 5 5 5 5 5 5 5 5 5 5 5 7002851 7396320 8116958 8773091 8969440 9166304 9362655 9559776 9887457 10149344 9952480 9690336 9035233 8246496 7063264 6274529 6142689 5681629 5352411 4825813 4562130 4430545 4233168 4166607 4166349 3968970 3902923 3836362 3835844 3769280 3637693 3570870 3505074 3438769 3372974 3372716 3306666 3306663 3240871 2451613 252 252 252 252 252 252 
252 252 252 252 252 252 4167608 4364736 4431042 4496839 4497097 4562901 4498136 4564188 4695263 4761812 4827875 4961007 3355700 3552822 3684408 1644825 6447714 9 10329243 5095149 5750760 6344688 250 250 250 250 5 5 5 5 5 5 5 5 5 3947580 3815994 3618615 3355443 3026478 723723 14417920 5 5 5 5 5 5 5 5 5 5 5 5 5 5 5 5 5 5 5 5 5 5 14952491 8315112 9101288 9428968 9625576 9887717 10084325 10412265 10609129 10674409 10346729 9560552 8772329 7523305 6800101 6274277 5813212 5418458 4891606 4562130 4364752 4298193 4232398 4166349 3968458 3968201 3901896 3704258 3638207 3572156 3439796 3505075 3439023 3372972 3241644 3306667 3306665 3240871 3109283 252 252 252 252 252 252 
252 252 252 252 252 13821419 4233410 4299716 4431045 4496840 4497358 4497622 4497623 4629467 4564185 4630235 4696547 4827877 4962293 3227205 12369084 11776947 11776947 9 11316396 6130847 5816807 6080232 7397622 250 250 250 5 5 5 5 5 5 5 5 5 13820387 9881289 3619129 3158064 250 250 5 5 5 5 5 5 5 250 250 250 250 250 250 250 250 5 5 5 5 5 5 5 5 5 5 8256767 10084842 10346211 10543073 10804961 11132385 11329251 11592164 11132899 10280929 9428961 7917539 6931940 6274020 5681630 5418203 4891351 4627923 4430288 4297939 4101075 4035024 4033738 3902408 3770567 3769793 3703229 3637433 3439795 3373746 3438768 3372459 3241644 3306667 3306665 3240872 3240100 2516883 252 252 252 252 252 
252 252 252 252 252 2524583 4233669 4299714 4431044 4497097 4497364 4497366 4563417 4497881 4629208 4630240 4761570 4827619 4893925 1647143 12829635 9 9 9 11908533 7042168 5751272 6146024 7132647 250 250 250 250 5 5 5 5 5 5 5 5 5 10679799 10478823 3160892 250 250 5 5 5 5 5 5 2389640 5489120 5489123 5158871 3108481 250 250 250 250 250 5 5 5 5 5 5 5 5 5 5 10021099 10870756 11067619 11264227 11657187 11853794 11984866 11199205 10215651 9297890 7786724 6866404 6405604 5681888 5417693 4825560 4562646 4495827 4167119 4100560 4100045 3902666 3836361 3770309 3703999 3571900 3506105 3504819 3373744 3307695 3372459 3306666 3306921 3306665 3240872 3240614 2517404 252 252 252 252 252 
252 252 252 252 252 3969717 4364739 4299713 4431044 4431562 4497108 4497366 4563160 4563161 4497874 4695262 4761569 4696546 5159674 1578001 11447982 9 9 9 9 8550002 5817324 6342888 7329769 9764863 250 250 250 7995392 5 5 5 5 5 5 5 5 15673642 10413543 250 250 250 5 5 5 5 5 8621994 5489131 5423332 5488866 5423330 5357538 5621483 250 250 250 250 250 14548992 5 5 5 5 5 5 5 5 5 11069676 11526372 11789030 11657700 11592164 11460835 11133412 10085350 9167077 7655141 6866148 6405603 5746914 5286878 4825818 4693719 4496084 4166607 4166352 4100047 3902667 3901895 3835844 3637950 3571898 3505592 3505074 3438769 3307694 3241644 3306667 3306921 3306665 3240872 3240614 3174305 11125714 252 252 252 252 
252 252 252 252 3837871 4167362 4364736 4364995 4430790 4365514 4497110 4497111 4497357 4562893 4563164 4563934 4629983 4761826 1511693 1710618 3092271 3815994 7500402 7631988 9 11776947 6854312 6606057 7527401 8775920 10616575 250 250 250 8585216 5 5 5 5 5 5 5 5 14828355 250 250 250 5 5 5 5 13580354 5555179 5554411 5488619 5357547 5423080 5422819 5422562 5091283 1842204 250 250 250 250 14614528 5 5 5 5 5 5 5 5 5 11133926 11068648 10937317 10871783 10740710 10609382 9888485 8970214 7523815 6932197 6470884 5681634 5286623 4891355 4759257 4561622 4297938 4034767 4034254 3967945 3835846 3704515 3703230 3637433 3570870 3373489 3439024 3372973 3306922 3306921 3306409 3175335 3240871 3240613 3174305 2319509 252 252 252 252 
252 252 252 252 3509422 4167358 4233664 4364996 4299461 4431049 4431576 4496855 4497102 4432079 4563417 4563932 4695519 4761313 1643794 1579032 3947580 3881787 4079166 3355443 12763842 9 10525851 6803433 7724521 8513776 9365225 4218206 250 250 250 5 5 5 5 5 5 5 5 5 250 250 6291456 5 5 5 5 4577023 5554667 5489132 5357548 5423083 5422572 5357036 5291235 5887231 1644310 3552822 250 250 250 250 9306112 5 5 5 5 5 5 5 5 5 9960703 10544616 10413030 10282472 10085608 9823463 8838631 7458793 7063526 6471396 5812450 5286369 4956635 4693721 4627158 4232145 4034511 4034254 3836360 3770566 3704001 3703485 3571384 3440054 3373746 3372974 3372973 3306667 3306922 3306664 3175080 3240871 3240356 3174563 3042463 15134193 252 252 252 
252 252 252 14149871 4100790 4232891 4233408 4364995 4299717 4430793 4431064 4497110 4497360 4431833 4563417 4629468 4695519 4630497 1378304 2565927 3815994 4013373 4144959 1710618 2697513 9 11842740 6607855 7461098 8185073 9234665 10940916 250 250 250 5 5 5 5 5 5 5 5 5 250 250 6225920 5 5 5 5 5620713 5620202 5488620 5357036 5422573 5291244 5357037 5356523 5555698 1511437 4737096 13027014 250 250 250 250 5 5 5 5 5 5 5 5 5 5 10020842 9955049 9758698 9497325 9431019 8642282 7589863 7128552 6602470 5746913 5286114 4956891 4693208 4495575 4100562 4099791 4033740 3836359 3835845 3769792 3572155 3506103 3439540 3439280 3307695 3372459 3306923 3306410 3306665 3240871 3240871 3240100 3174563 3042976 3239319 252 252 252 
252 252 252 2786216 4166335 4232381 4298946 4364739 4364741 4431049 4431318 4431576 4497359 4431576 4563418 4629469 4564189 4695777 4895733 3746852 3880242 4013115 2697513 986895 12303291 9 9 11184295 6806520 7986669 9102576 10217966 8101537 250 250 250 5 5 5 5 5 5 5 5 5 250 9437184 5 5 5 5490156 5619945 5488617 5357034 5357037 5357038 5356526 5225198 5290989 5291247 1246720 5921370 11842740 9 4671303 250 250 250 5 5 5 5 5 5 5 5 5 14435912 9234158 10461088 11645618 9 11776176 7655402 7063016 6405093 5549282 5088736 4890588 4627415 4429526 4166098 3968462 3902668 3901638 3704514 3638463 3637179 3571382 3505331 3439023 3372974 3241643 3306921 3306408 3175591 3240870 3240359 3109029 3174049 3042975 2582423 252 252 252 
252 252 252 3640496 4166595 4232638 4298946 4233669 4364742 4365001 4430806 4365528 4497112 4431578 4562907 4563419 4564189 4695519 4761570 4828136 4830196 5028090 2108983 13355722 9 9 9 9 9733249 7919850 9035754 10020331 11201005 250 250 250 250 5 5 5 5 5 5 5 5 5 12713984 5 5 5 4510975 5488619 5422827 5356523 5356779 5290990 5225198 5290734 5290479 5291250 1180928 6381921 11776947 9 9276813 250 250 250 15269888 5 5 5 5 5 5 5 5 5 11315379 12763328 9 9 9 6999536 6734056 6141667 5220322 4104676 6005204 4102105 4363476 4034769 3968205 3967946 3770565 3704258 3638207 3637178 3570869 3504819 3439024 3372972 3241644 3306922 3306410 3306664 3240870 3240614 3109283 3174050 3108512 2976925 252 252 252 
252 252 252 4100275 4166593 4232638 4298435 4298692 4364486 4299721 4430805 4431065 4496858 4497113 4562907 4497883 4629214 4695519 4696034 4696292 4762341 4828391 4761309 2697513 9 9 9 9 11776947 7721448 8706539 9428971 10283242 11993087 250 250 250 8716288 5 5 5 5 5 5 5 5 5 5 5 5 4510463 5422829 5422315 5290732 5225453 5290989 5290478 5290735 5224688 5423869 1050886 9079434 9 12303291 3289650 250 250 250 250 5 5 5 5 5 5 5 5 5 5 9284780 9 9 9 8372441 6405351 5878243 4498145 12497836 11645617 12170159 11186355 4099791 4033740 3967946 3835588 3769793 3703485 3506105 3440054 3505075 3438510 3372973 3241644 3306923 3306666 3306665 3240870 3240614 3109283 3174050 3108512 2976925 252 252 252 
252 252 252 4100277 4166077 4232641 4298692 4298950 4299208 4299722 4431060 4431320 4497113 4497370 4431835 4563420 4629214 4629470 4695777 4761571 4696549 5159934 2104346 2236962 7829367 11776947 10526880 1842204 13027014 11776947 9602433 8445942 9101804 9300716 10682367 250 250 250 5 5 5 5 5 5 5 5 5 5 5 5 4378623 5422063 5290734 5290479 5290480 5224689 5159409 5224433 5224690 5162239 8617853 11908533 9 10987431 3421236 12369084 263172 250 250 250 5 5 5 5 5 5 5 5 5 5 11447982 11513775 11579568 9 11711153 11907760 11055285 9 9 9 11842225 4033998 3902410 3836359 3769795 3704000 3637436 3571382 3505333 3505075 3307695 3372461 3372716 3306667 3306921 3306665 3240870 3240614 3174308 3043232 3108512 2976925 8167870 252 252 
252 252 10733785 4100280 4166078 4232384 4298693 4298951 4233671 4299722 4431062 4431319 4497113 4496858 4497371 4563163 4498141 4629215 4695521 4630243 4761828 2703441 2236962 2368548 4144959 4079166 4079166 2565927 1776411 11776947 11776947 9997963 8379886 8513005 8711406 250 250 250 3997696 5 5 5 5 5 5 5 5 5 5 5 4312831 5356271 5290223 5159408 5159152 5224434 5224434 5158642 5158899 5394510 11119017 9 9 9 12632256 12961221 13158600 250 250 250 11993088 5 5 5 5 5 5 5 5 5 15335423 16579836 16448250 14606046 13158600 11316396 9 9 9 9 11842225 4033741 3967690 3901639 3704002 3703742 3571898 3505590 3505076 3373489 3307695 3372973 3372715 3306922 3306921 3306665 3240871 3240614 3174308 3043232 3108512 2976925 2055824 252 252 
252 252 3901873 4100281 4166335 4232385 4233158 4298950 4233673 4365002 4430549 4430807 4365785 4497112 4497113 4497628 4563420 4498142 4563936 4695527 4761571 2901075 2368548 2434341 4079166 4144959 4079166 2631720 2697513 5395026 9 9 8815234 7791347 8316655 6071721 250 250 250 5 5 5 5 5 5 5 5 5 5 5 4246527 5290225 5158897 5224690 5224433 5158643 5093108 5158387 5159162 9539984 9 9 9 9 9 10855845 11974326 5526612 250 250 250 5 5 5 5 5 5 5 5 5 13766415 5395026 6381921 9079434 10921638 13355979 16053492 12763842 11513775 9 11711153 2918095 3836359 3770308 2850497 9479349 3637177 3439541 3504818 3373746 3307693 3372973 3372715 3307178 3306921 3306409 3240871 3240614 3174819 3043232 3107998 2976925 2055822 252 252 
252 252 3048109 3968702 4034751 4101315 4167111 4298951 4233673 4364748 4299478 4431063 4431321 4365786 4497115 4497371 4431838 4563167 4629216 4564193 4695523 4761574 3498107 3092271 4144959 4012600 2828326 2763306 2565927 9 9 9 9 11974069 8563121 7396341 5150634 250 250 250 5 5 5 5 5 5 5 5 5 5 4049407 5224179 5158643 5092851 5158387 5158388 5092853 4699897 9010808 9 9 12500670 12171705 9 9 6184542 3750201 11842740 250 250 250 5 5 5 5 5 5 5 5 5 5 10885915 3947323 3947580 3815994 3684408 4144959 6710886 13224393 252 13092807 9 11842225 10004917 11645362 9 9 11514034 3111089 3438769 3372717 3372972 3372461 3241644 3306921 3306409 3240870 3240614 3109283 3043233 3107999 2976925 2844566 252 252 
252 252 3507887 4034496 4034752 4101315 4167367 4298441 4233418 4364749 4299734 4431063 4431319 4431064 4431578 4496863 4497115 4431837 4497887 4629217 4695266 4695780 4762087 4556466 4755903 5225211 5423100 2697513 2236962 9 9 9 9 11908533 9 10524050 7450567 250 250 250 250 5 5 5 5 5 5 5 5 5 3983359 5093108 5158389 5158132 5092596 5027060 6450032 11053223 9 9 12763842 3684408 11974326 11776947 10724259 5197647 9 9 250 250 250 7536640 5 5 5 5 5 5 5 5 5 5 3031104 3815994 3815994 3750201 3618615 3552822 3552822 6118749 10790052 14737632 11513775 9 9 9 9 12039346 2651313 3439023 3372717 3372972 3372461 3307180 3306921 3306408 3240870 3240614 3109283 3043233 3108255 3042461 2975895 11519446 252 
252 252 3901617 4034497 4035009 4166341 4232903 4298441 4233163 4365005 4365270 4431063 4430809 4431322 4431068 4497115 4497114 4497372 4563166 4563425 4563938 4695525 4761573 4696039 4827882 4959466 5091307 4224147 2763306 10197915 11776947 9 12961221 1907997 12040119 9 11842740 12565949 250 250 250 5 5 5 5 5 5 5 5 5 3721983 5092597 5092596 5092596 4831999 7238518 11908533 9 9 11908533 2105376 12566463 9 9 9 9 9 11513775 8882055 250 250 250 5 5 5 5 5 5 5 5 5 5 6448268 2892314 3881014 3750201 3684408 3618615 3487029 3355443 3552822 10329501 16645629 13355979 9 9 9 11643042 3373490 3438511 3372718 3372972 3372461 3307180 3306923 3306408 3240870 3240614 3109284 3043233 3108255 3042461 2844823 6195628 252 
252 12309988 3901875 4033982 4034498 4166597 4232648 4298698 4298954 4364750 4364758 4299734 4431063 4430809 4431322 4431321 4365530 4497115 4431581 4563167 4498145 4564196 4695269 4695781 4696297 4762090 4959466 2638161 2894892 3092271 2960685 3289650 3618615 3289650 3355443 2105376 11776947 9 526344 250 250 250 5 5 5 5 5 5 5 5 5 4565977 7963529 11313821 11776947 9 9 9 9 9 9 5263440 9 9 9 9 9 10000536 3750201 722435 250 250 2818048 5 5 5 5 5 5 5 5 5 5 4561374 4430043 4496095 4034255 2958107 3487029 3355443 3289650 3289650 2894892 7039851 16448250 11316396 9 3767732 3439023 3307439 3372974 3372972 3372459 3307178 3306923 3306408 3240871 3240613 3109285 3043233 3107999 3042461 2844823 1135237 252 
252 6857411 3901878 4034238 4100035 4166340 4232647 4167370 4298700 4364494 4365016 4365270 4431065 4431064 4430810 4431322 4431322 4431580 4496861 4431581 4563167 4629218 4564195 4695269 4761321 4696041 4827624 2827811 2960685 3223857 3881787 4013373 3289650 3421236 3355443 921102 11776947 9 13092807 250 250 250 3997696 5 5 5 5 5 5 5 5 15803942 9 9 9 12500670 3881787 11316396 9 9 9 12566463 9671571 11908533 9 9 9 11842740 3627636 5621503 250 250 250 5 5 5 5 5 5 5 5 5 5 3972579 4363993 4297942 4100306 4100305 3033955 3354154 3289650 3158064 3158064 2829099 7434609 16382457 9 11776690 4883119 3373229 2585005 2585004 2716075 3307178 3306922 3306409 3240872 3240614 3109285 3043233 3107999 3042461 2844823 1595272 252 
252 1864103 3901367 4034240 4100291 4166342 4232649 4167371 4298444 4233687 4364757 4364759 4365015 4431065 4431065 4430811 4431324 4365533 4497118 4496861 4431839 4497888 4629218 4563940 4629990 4695784 4696040 2628112 3158064 3092271 4079166 3881529 3289650 3421236 3487029 921102 11776947 9 9 8816262 250 250 250 5 5 5 5 5 5 5 5 5 11515574 9 10790052 3684408 2763306 2829099 7895160 9 12632256 3552822 3355443 12369084 9 11513775 11382189 11513775 11710123 6843246 250 250 250 5 5 5 5 5 5 5 5 5 5 3187949 4232150 4166356 4034511 3968204 3836360 3969750 2836059 3223857 3026478 3026478 2697513 6447714 15066597 9 11776690 9150640 12104882 11908018 12695986 3307178 3306921 3306410 3240870 3240614 3109285 3043233 3107999 3042461 2844823 2121100 252 
252 2258090 3836082 3902912 3968707 4035270 4166857 4232651 4167115 4298961 4233684 4364758 4365014 4299737 4365016 4431066 4431065 4430810 4431324 4365788 4496861 4431839 4563168 4563682 4563941 4629733 4695270 4696040 5160703 4010023 4624579 4894194 12039603 12697792 12105912 4144959 2631720 8026746 12171705 7566195 8618883 250 250 250 5 5 5 5 5 5 5 5 5 11645618 9 3947580 2829099 3092271 3289650 3092271 3026478 2171169 2171169 9 9 9276813 8553090 12829635 13750737 11513775 11842740 250 250 131072 5 5 5 5 5 5 5 5 5 5 4100563 4034512 3968204 3902154 3770309 3769795 3769537 3837392 2499616 2960685 2829099 2763306 3421236 11316396 9 9 9 9 9 9281712 3241129 3306408 3240870 3240614 3109283 3043232 3107998 3042461 2844823 2120844 252 
252 2521004 3835569 3968447 3968962 4034758 4101320 4232649 4167114 4298448 4298709 4364758 4365014 4364760 4365272 4299480 4430809 4431067 4431068 4431324 4365533 4496862 4431840 4563169 4563426 4629220 4563941 4629991 4761576 4762351 4761836 5092862 12500670 9 9 11908533 2565927 3618615 3355443 2829099 11974326 250 250 250 15532032 5 5 5 5 5 5 5 5 12294810 11776947 7433836 3026478 3289650 3355443 12763842 11776947 11974326 12303291 9 11776947 3355443 3552822 3684408 11513775 252 12105912 250 250 250 5 5 5 5 5 5 5 5 5 5 3511769 4033997 3967946 3901895 3835588 3769537 3638207 3571899 3571642 2705246 2302755 2829099 7829367 9 9 9 9 9 9 7372682 3306922 3306665 3240871 3240614 3174819 3043232 3108254 3042205 2844823 2646672 252 
252 2520747 3835828 3967935 3968705 4100548 4166344 4232650 4232906 4298448 4298965 4233429 4364758 4365014 4364759 4365273 4299738 4365017 4431066 4430811 4431067 4365533 4497119 4431839 4563170 4497891 4629220 5154018 4170988 4761322 4696043 3766437 12237498 9 9 9 12763842 4408131 4671303 3881787 9 1118481 250 250 250 5 5 5 5 5 5 5 5 5 2702139 4500986 3025705 3355443 3618615 12434877 9 9 9 9 11447982 3750201 3355443 3289650 3355443 7631988 14408667 250 250 250 5 5 5 5 5 5 5 5 5 5 8624791 3572931 3901896 3770565 3704258 3638207 3703229 3310016 3175079 6450033 11382189 11908533 9 11579568 11447982 11579568 9 11776947 8947848 3243450 3306410 3306665 3240615 3240614 3174563 3043233 3108255 3042204 2844823 2646672 252 
252 2455209 3835319 3968192 4034241 4100037 4166344 4101321 4232651 4167122 4298708 4298965 4298965 4299223 4364503 4365015 4364760 4364761 4299738 4299739 4365276 4431068 4430812 4365790 4497377 3973609 12497836 9 11645362 8760520 4830463 591107 11053224 9 9 9 11579568 11513775 11513775 11447982 9 11776947 328965 250 250 250 5 5 5 5 5 5 5 5 5 3586303 4761843 4763647 1906451 7500402 12303291 9 9 9 10724259 3562361 3223083 3289650 3289650 3223857 3026478 65793 250 250 5 5 5 5 5 5 5 5 5 5 11514803 9 11908275 9407625 4553380 8815230 11052450 11842740 9 9 9 11579568 12829635 10592673 9145227 13421772 11579568 9 8354423 3306921 3306664 3175335 3240359 3240356 3174307 3042721 3107997 3042204 2910102 2646673 252 
252 2454954 3704503 3967935 3902659 3968708 4100807 4166345 4166601 4232913 4167122 4298451 4298964 4298710 4233685 4364503 4364503 4365016 4365016 4364762 4365273 4299740 4299483 4431069 4365534 2309457 13224393 9 9 11645362 11184810 11974327 9 11579568 12171705 14606046 16382457 16382457 14737632 15329769 14803425 9 13158600 250 250 250 5 5 5 5 5 5 5 5 5 5 4630000 4961791 1512466 3355443 2894892 5789784 11776947 9 10461086 4563434 4829951 2563351 3289650 3289650 3289650 1513239 250 250 14876672 5 5 5 5 5 5 5 5 5 15626609 12500670 9 9 11842740 9 9 9 9 9 12698049 13027014 8882055 3684408 3618615 3881787 11316396 9 12302003 3110057 3109544 3240615 3240357 3174565 3174306 3042719 2976669 3042204 2910102 2646671 252 
252 2454700 3769526 3836611 3902401 4034244 4100549 4166344 4100808 4232656 4232913 4232915 4298452 4298709 4298964 4298966 4233430 4299224 4364504 4364760 4365016 4364760 4364762 4299482 4564458 1708814 1513239 9 9 9 9 11579568 12961221 14803425 13750737 8618883 6710886 5855577 4671303 4671303 9803157 9 9 7434609 250 250 13107200 5 5 5 5 5 5 5 5 5 8962007 3970781 2763306 3487029 3618615 3881787 12829635 9 10724002 4431848 4497126 4497384 2630431 3289649 3289650 3552822 250 250 2686976 5 5 5 5 5 5 5 5 5 12716554 3947580 11316396 9 9 9 9 9 9 13355979 9013641 4605510 3815994 4079166 3421236 1710618 9013641 11776947 9 12564658 12630194 10726065 2649765 3109285 3174563 3108512 2976670 3042203 2910102 2646159 252 
252 2388906 3769270 3901885 3967679 4033986 4100294 4034758 4166087 4101326 4232400 4232657 4167121 4232914 4298705 4298706 4298707 4298963 4298708 4298708 4233428 4233429 3905495 3905496 2041645 2039583 2368548 11908533 9 9 12632256 11250603 5723991 3815994 3881787 4079166 4079166 4079166 3815994 2829099 2565927 11250603 9 10461087 250 250 6094848 5 5 5 5 5 5 5 5 5 5 11191492 9211020 3618615 3750201 2697513 6118749 9 11316396 4300520 4431075 4365282 4299488 4431590 3434900 3355443 250 250 250 5 5 5 5 5 5 5 5 5 5 2961199 1579032 8684676 9 9 11447982 12105912 7303023 3947580 4013373 4013372 3288618 2965584 2368033 1973790 5526612 10790052 9 9 9 9 9 3109027 3174049 3108255 2976924 2910874 2909845 2580878 252 
252 2388649 3637946 3770299 3836606 3902912 3968709 4100293 4035014 4166606 4101325 4232654 4232910 4232911 4167119 4232911 4233168 4298448 4298448 4298704 4298705 4167634 12629165 12235695 6513249 1250067 4210752 9 9 12171705 8355711 4013373 3881787 4013887 4209981 4144445 4144445 4275517 3486513 1973790 2368548 11513775 9 11447982 250 250 3866624 5 5 5 5 5 5 5 5 5 5 5 11586249 3486257 6842472 12434877 12237498 9 11579568 4104172 4299489 4364768 4299230 4233437 4298716 3303827 131072 250 250 5 5 5 5 5 5 5 5 5 5 2763820 2302755 4671303 11776947 9 10592673 4342338 3947580 4013373 3748397 3177657 3372716 3306923 2842503 1973790 2105376 9803157 9 9 9 9 12105139 2386594 3174050 3107998 2976412 2910874 2909845 2580365 252 
252 1994149 3703477 3835834 3836349 3967935 4034243 4100292 4100549 4166091 4166348 4101323 4232651 4232396 4232652 4232909 4232653 4167117 4167373 4232910 4298702 8168640 11645618 9 9 12237498 9 9 11447982 5921370 3684408 3947580 4342338 250 5 5 5 5 4763382 1775638 2236962 11316396 9 11776947 250 250 262144 5 5 5 5 5 5 5 5 5 5 5 15992324 1917791 11842740 9 9 9 11776947 3841513 4364766 4233436 4298716 4232923 4167386 4166871 1720672 250 250 5 5 5 5 5 5 5 5 5 5 2697770 2105376 1381653 12171705 9 11119017 4013373 4144443 3229787 3372974 3372716 3307180 3307179 3374260 1840914 1710618 8289918 11184810 9 12434877 12237498 4011311 3109543 3043232 3108254 3042203 2910360 2909332 2054792 252 
252 1533862 3637426 3770041 3836092 3902398 4033985 4034498 4100290 4034760 4100808 4166343 4166600 4166856 4232392 4232649 4232648 4232649 4232393 4232393 4232650 1841946 13224393 9 9 9 9 10855845 4671303 3947064 3222053 3176613 250 250 250 5 5 5 10114166 1842462 2039583 11184810 9 9 250 250 250 5 5 5 5 5 5 5 5 5 5 5 5 4199701 12566206 9 9 9 9 9011321 4233179 4167385 4232665 4166871 4101078 4100820 3836103 250 250 5 5 5 5 5 5 5 5 5 12724025 3638723 2039583 1052688 11908533 9 11118760 3243450 3307179 3307179 3307179 3306922 3306667 3306923 3306923 3307179 1907997 4539717 10526880 9 7105644 4013373 3043494 3174306 3108255 2976668 3041690 2976152 2843795 1923206 252 
252 6921410 3636914 3769783 3770041 3902140 3968191 4034239 3968960 4100037 4100548 4100804 4166340 4166340 4101060 4101317 4166598 4166598 4232390 4232390 4432346 2697513 2500134 10592673 9 9 9 7500402 3684408 4302050 4299215 4431574 250 250 250 5 5 5 5 272172 1710618 10987431 9 9 250 250 250 5 5 5 5 16384000 5 5 5 5 5 5 5 5 4989474 8487297 11579568 12500670 9 11447724 3642845 4166871 4100822 4166357 4100564 4100050 4431590 250 250 5 5 5 5 5 5 5 5 5 13442605 3570869 1775637 3750201 9 9 10789537 3306923 3306923 3306667 3306667 3306923 3306923 3306921 3306922 3307182 1710618 3552822 10329501 9 8158332 4079166 3174822 3174306 3108254 3042204 2910873 2975895 2843794 1397120 252 
252 12308963 3571120 3769521 3769783 3836089 3967677 3902909 4033981 4034499 4100034 4100546 4100802 4166083 4166338 4166339 4166339 4166595 4101059 4101060 3169139 2829099 3092271 3355443 9 9 10263708 3354927 3965870 4167114 4232907 4232908 250 250 250 12976128 5 5 5 5 1055515 10724259 9 9 250 250 4456448 5 5 5 5 5 3473408 5 5 5 5 5 5 5 5 12819869 11776947 4802889 12105912 11776947 7697009 4166357 4035027 4034770 4034513 3968719 4496869 250 250 5 5 5 5 5 5 5 5 5 7165311 3111091 6972254 12237498 9 9 8815747 3306921 3306921 3306921 3306922 3306921 3306921 3306409 3306408 3306665 1710360 3355443 10066329 9 12105912 9209731 2583200 3042977 3107999 3041948 2910617 2844566 2843537 1002363 252 
252 16777214 3505071 3703217 3769524 3835830 3901881 3967673 3967930 4033983 3968957 4034494 4100030 4100543 4034751 4100545 4166082 4100546 4166083 4233421 1709330 2171169 2500134 789516 9 11184810 7500145 4166604 4166346 4101069 4166606 4166864 4629993 250 250 250 5 5 5 5 5 10139061 11710897 9 250 250 5 5 5 5 5 5 250 5 5 5 5 5 5 5 5 5 11321279 9 6974058 9 11908533 4097212 3968720 4033999 3968462 3902412 2314615 250 15728640 5 5 5 5 5 5 5 5 5 11321022 11645362 9 11513775 12829635 10263708 2638166 3306409 3306409 3306409 3306409 3306408 3306664 3306665 3240871 3175079 1644051 4144959 10329501 9 9 9 9 13352885 2845341 2976154 2975895 2909589 2777743 6063268 252 
252 252 3045036 3572144 3637938 3704501 3836087 3902136 3967672 3902909 4034236 4034493 4034493 4100285 4100031 4100543 4100289 4100290 4034755 4103126 13092292 12040119 12040119 12500670 9 10461087 4348522 4100298 4035021 4166350 4166352 4166610 4166869 132102 250 250 250 5 5 5 5 5 15087929 11720920 250 5 5 5 5 5 5 5 250 250 5 5 5 5 5 5 5 5 5 10911615 8817033 9 9 11315107 3968461 3902668 3967947 3902411 250 250 5 5 5 5 5 5 5 5 5 5 11645618 9 12105912 15921906 9671571 4078650 3308985 3306665 3306665 3306665 3306665 3306665 3240871 3240616 3240872 3240871 1577485 3947580 10987431 9 9 9 9 12170931 2911132 2910617 2910358 2909844 2777486 11387346 252 
252 252 2518951 3571630 3637679 3769778 3835829 3901878 3836343 3967931 3902651 4033979 4034237 4034492 4034237 4100287 4100031 4100032 4034499 1518907 12171705 9 9 9 11776947 9671056 3577305 4034252 4100302 4100304 4035026 4100563 4100820 4563434 250 250 250 12713984 5 5 5 5 5 5 5 5 5 5 5 5 5 5 250 250 250 5 5 5 5 5 5 5 5 5 15796746 11515831 11710897 9 4949170 3902154 3836616 4166614 250 250 5 5 5 5 5 5 5 5 5 12619663 11710897 9 10000536 7566195 3618615 3296095 3175336 3175079 3175079 3175079 3175079 3240616 3240872 3240870 3240871 3240615 1511950 6579300 11579568 9 12369084 11908533 11908533 11251634 3041947 2976152 2844309 2778515 2580363 252 252 
252 252 3241126 3571114 3637165 3703471 3770035 3835827 3836084 3836344 3902392 3968185 3968442 3968441 4034235 4034238 4034237 4034492 4234192 1512981 7039851 11776947 9 9 11513775 7498598 3968971 3968461 4034254 4034255 4034256 4034513 4034512 4034513 4497384 250 250 250 5 5 5 5 5 5 5 5 5 5 5 5 5 5 2318 250 250 250 15859712 5 5 5 5 5 5 5 5 5 5 15347760 12816785 6788518 3247309 10289152 5 5 5 5 5 5 5 5 5 5 5 9 9 9 4737096 3947580 3621451 3175078 3240615 3240615 3240615 3240871 3240870 3240615 3240615 3240614 3240614 3240614 1380107 9605778 11776947 12434877 3684408 4079166 4144185 2912679 2976154 2844567 2909844 2843536 1725313 252 252 
252 252 10534614 3504806 3505579 3637677 3769520 3770033 3835569 3901878 3902135 3902391 3968184 3967929 3902649 3968185 4033978 4034237 1842977 3092271 3421236 2697513 10329501 11776947 9 7765379 3902667 3967948 3902668 4033741 4033998 4033998 4033998 4033998 4034255 250 250 250 250 5 5 5 5 5 5 5 5 5 5 5 5 5 3578850 250 250 250 250 4128768 5 5 5 5 5 5 5 5 5 5 5 5 5 5 5 5 5 5 5 5 5 5 5 5 10631995 11776947 9 9 5131596 2962490 3175078 3240613 3240613 3240613 3240613 3240357 3240357 3240613 3240613 3240613 3240100 3109285 6579041 11053224 9 7434609 4013373 4079166 3950158 3042204 2910361 2910102 2778514 2711950 1593470 252 252 
252 252 252 3439023 3439781 3637419 3638189 3769519 3704495 3770548 3836085 3901876 3836600 3967668 3967926 3967929 3902650 3902653 1313542 3355443 3487029 3684408 3618615 11382189 9 8682099 3902669 3967947 3967691 3968203 3902667 3902667 3902668 3902668 3902668 2314871 250 250 250 250 5 5 5 5 5 5 5 5 5 5 5 15535379 3968976 4431332 250 250 250 250 250 5 5 5 5 5 5 5 5 5 5 5 5 5 5 5 5 5 5 5 5 5 5 5 4277316 9 9 9 4222353 3174821 3174564 3240356 3240357 3240613 3240613 3240613 3240613 3240613 3240100 3109285 3174819 3109801 8750469 11776947 9 12040119 8026746 3947580 2911649 2910618 2975895 2909844 2843793 2777485 8166324 252 252 
252 252 252 3372714 3373487 3571112 3571883 3703469 3703724 3704241 3835827 3770546 3901874 3901876 3836343 3836601 3836601 3902139 3155230 3421236 3618615 4013373 1381653 8816262 11776947 9274494 3771083 3901896 3901640 3901896 3901896 3902152 3836616 3836360 3901895 1580837 9276813 250 250 250 250 5 5 5 5 5 5 5 5 5 15995149 3772369 4033740 4033996 4033739 4430816 250 250 250 250 250 11075584 5 5 5 5 5 5 5 5 5 5 5 5 5 5 5 5 5 5 2066116 1710360 1776411 10921638 9 9 5269886 3174307 3174563 3174819 3174820 3109284 3109284 3109284 3109284 3174820 3174564 3174306 2781867 8024684 11776947 9 9 9 9 11974068 2779545 2976153 2844310 2778001 2711951 2711435 252 252 252 
252 252 252 2846625 3307438 3439531 3571625 3572139 3703467 3769519 3704240 3835566 3770289 3770291 3901877 3901880 3901881 3902138 3904203 3487801 3289393 11119017 13092807 12040119 9 9801868 3640013 3836103 3836102 3836102 3836102 3836359 3836102 3770310 3835845 1315345 8487297 13224393 250 250 250 250 12124160 5 5 5 5 5 5 5 11317167 3704775 3902410 4033482 4033482 4033481 4232148 250 250 250 250 250 250 15335424 5 5 5 5 5 5 5 5 5 5 5 5 5 5 11862016 1803200 3307181 1643279 1447446 10197915 9 9 6253429 3174562 3174562 3174307 3174308 3174564 3174307 3174307 3174307 3174307 3174562 2978215 7235682 11316396 9 12171705 11842740 9 9 12303033 2976153 2975639 2909845 2778000 2777485 2579848 252 252 252 
252 252 252 1597589 3241388 3373731 3571115 3637161 3572138 3638190 3769260 3703983 3835312 3835825 3770292 3770295 3770297 3901881 3901630 3901889 2570823 9 9 9 9 11118759 3246544 3835845 3835589 3835588 3835589 3835845 3835587 3704515 3836361 1447446 8026746 11776947 2894892 250 250 250 250 250 15597568 5 5 15335424 6822169 11976639 11842740 5664128 3902151 4033224 4032967 4032967 4032966 4033224 4298200 250 250 250 250 250 250 3670016 15335424 5 5 5 5 5 5 5 15138816 8126464 983040 870762 3241130 3240357 3174564 1576968 1644825 9408399 11776947 9 6121843 3174049 3174306 3174563 3174563 3174563 3174563 3174563 3174306 3174305 3043236 6971995 11842740 9 12369084 2697513 2697513 11579568 12171705 5524550 2975640 2844310 2778259 2711950 2645900 2185090 252 252 252 
252 252 252 12111325 3240615 3372712 3504804 3505572 3506097 3572137 3703211 3638189 3769519 3769776 3704242 3770035 3835573 3835833 3835580 3836097 1579032 9 9 9 9 11776947 8814974 3704514 3704258 3769794 3769537 3769537 3704000 3703744 3311821 9342606 11776947 9 9 11842740 6847113 250 250 250 250 250 250 1907997 6908265 11842740 9 9143165 3770825 4032965 4032965 4032709 4032708 3966658 3966658 3967945 1643021 1907997 460551 250 250 250 250 250 250 250 250 250 250 250 723723 11513775 11974326 11116955 4157846 2780579 3108255 2709113 1710875 6974058 11119017 9 6187893 3108512 3042977 3043232 3108769 3108769 3108769 3043232 2714010 7695975 10724259 9 9 9 2960685 3355443 3684408 3881787 3947321 2911906 2844565 2909844 2843793 2646157 2579848 2776195 252 252 252 
252 252 252 252 2386075 3306666 3439012 3505062 3505320 3571636 3571629 3637676 3638190 3638190 3703728 3769779 3769781 3704249 3770045 1776412 1710618 6908265 11842740 12698049 12303291 9 10920864 3769536 3769536 3704000 3703743 3638207 3311304 6316901 10921123 9 9 9 9 9 9 3049681 3637950 3240872 3240614 4100048 3903698 1052688 8158332 9 9 11776946 4096696 4032451 3966914 3966658 3900865 3900864 3966400 3966400 2440014 1710618 7500402 12566463 13027014 3158064 3617584 1720157 1381653 1447446 1381653 5460819 4276545 3552822 3355443 2763306 11447982 9 11776947 12302002 5994382 2320802 1381138 6908265 9 9 7106419 3042976 3108511 3108511 3042976 2650024 2648219 4482432 11250603 11842740 9 9 9 9 12500670 2894892 3684408 3815994 3291195 2844567 2844052 2843794 2712207 2645642 2513797 15002351 252 252 252 
252 252 252 252 2779546 3240614 3307427 3439013 3505062 3571112 3505833 3637425 3637677 3703215 3703473 3703731 3703989 3703737 3902664 1710360 1579032 3815994 3947580 3881787 986895 9 11776947 3441859 3637950 3703486 3638208 3372200 10460572 11908533 9 9 9 9 11513775 11447982 9 12302260 8822965 2849208 3441345 3507137 3311305 11447982 9 9 9 9 11974069 4293560 4097986 4097985 4163522 4163522 4229313 4163521 4362962 1710103 7631988 11316396 9 10658466 4621234 1980493 3092271 3092271 3092271 4013373 3881787 3289650 3355443 3421236 13027014 9 9 9 9 11974325 11908533 11842740 9 9 11842740 7766926 2845598 4482173 8024941 10592157 11382189 11908533 9 11776947 12171705 11842740 9 9 9 9408399 3815994 4077620 2845599 2909845 2844051 2843794 2777743 2579848 1658747 252 252 252 252 
252 252 252 252 252 2845597 3240868 3372705 3373219 3504807 3439784 3571114 3571630 3637165 3571890 3637690 3637685 3703223 3770307 1577228 3684408 3881787 4013373 4408131 1973790 4671303 9 11380900 5800354 8354164 11579568 9 9 11579568 9 14145495 16119285 14671839 9211020 10132122 16514043 12434877 11513775 9 11645618 9 9 11579568 11579568 11974326 9 11579568 9 9 11908275 6981533 4492227 4557763 4492226 4425920 4493001 1577230 8882055 11776947 9 9 9 9 2829099 3158064 4079166 3815736 3288876 3421236 3487029 1447446 12895428 9 9 9 2368548 3618615 9868950 12105912 9 9 9 9 9 9 11776947 9 9 9 9276813 3947580 4013373 2894892 7631988 12171705 11513775 2831421 2845856 2845083 2909844 2778259 2447746 2182770 1984617 2579590 10992330 252 252 252 252 
252 252 252 252 252 1201804 3174822 3306660 3372707 3439013 3439271 3439786 3571373 3505839 3571375 3637170 3637428 3571896 3571899 2576238 3881787 3947580 4079166 2368548 526344 12895428 9 9 11776947 9 9 11579568 13948116 16185078 14869218 9079434 6250335 4276545 3881787 3158064 5329233 12698049 16711422 13882323 12829635 12237498 12237498 14869218 13355979 11908533 14606046 15921906 12237498 9 9 11776947 8227735 4296137 4623554 4557248 4624329 1511693 8750469 11776947 9 9 9 9 2634297 3157806 4077878 3175851 3110059 3357763 3487029 1710618 5066061 12171705 9 12105912 3815994 3881787 3947580 9079434 9 9 9 12105912 5460819 5197647 2039583 9 9 9 12237498 3552822 2434341 3092271 3355443 2631720 3815736 2845600 2844566 2909845 2844051 2843537 2777486 2976154 2381438 1921403 252 252 252 252 252 
252 252 252 252 252 13491174 3042976 3240610 3306656 3307428 3439013 3439272 3439531 3440045 3571118 3505841 3571381 3571639 3637433 3637950 3572157 3822181 4085612 1643793 12303291 9 9 9 9 9 13882323 15329769 9342606 6776679 4539717 3881787 4013373 4079166 3684408 3223857 3355443 3881787 6447714 10395294 12040119 12895428 13421772 8224125 5658198 3881787 4210752 7960953 13290186 14606046 11579568 11579568 9 11446435 4950201 4688576 4755142 1314313 9671571 9 9 12040119 12040119 11974326 2452644 3370912 3241130 3108511 3173534 3107740 1777185 1776411 3684408 2960685 3947580 3355443 3881787 3815994 4079166 1579032 9 9 9 12237498 4144959 4210752 1710618 13421772 9 9 11776947 3092271 2829099 3223857 3421236 4013373 3814191 2844567 2909589 2778259 2843537 2712464 2711951 3108256 2380922 1789559 252 252 252 252 252 
252 252 252 252 252 252 2910361 3042976 3109021 3306658 3372709 3307685 3439016 3373739 3504813 3439792 3505331 3505333 3571127 3571383 3571127 3571127 3571383 2371384 12566463 9 9 9 9 11776947 6579300 3881787 4079166 4079166 4079166 4143928 3353639 2439755 3024932 3355443 3487029 3618615 3750201 3815994 3947580 4013373 3815994 3947580 3947580 3881787 3552822 3552822 3421236 4868682 9079434 14935011 13948116 11513775 9 11051419 6196142 4275771 11776947 9 12369084 4013373 4079166 4078907 3371169 3305119 3173790 3173275 3107482 3041689 1511176 3815994 3684408 3750201 3947580 3946032 3881530 3947580 1907997 1842204 5066061 9145227 12566463 9 4144959 3026478 2236962 2631720 7105644 6184542 3354670 2847918 3024415 3289650 3487029 3947065 2845341 2909844 2778514 2843793 2712207 2711949 2579849 2645640 2513024 252 252 252 252 252 252 
252 252 252 252 252 252 1003908 3042204 3042969 3174815 3240866 3306916 3307432 3373225 3439020 3439279 3439280 3505074 3439540 3439797 3439797 3505333 3573444 2236188 986895 12566463 11974326 12566463 10395294 9 9737364 3684408 4143928 3551276 2904688 3374777 3372974 3307180 3373231 3173791 3024416 3750200 3881787 3947580 4079166 4144959 3947580 3946548 2696739 3222310 3552822 3552822 3552822 3487029 3223857 4605510 10921638 16382457 14671839 11579568 11776947 11842740 9 9 5789784 4079166 4013373 3949901 3239582 3304861 3238811 3041689 3041432 2910102 2500133 3684408 3618615 3684408 3617583 2845081 2779806 3301252 1710360 1842204 4144959 4013373 3815994 3749429 4340791 1644825 2434341 2697513 4210752 4013373 3622998 2975639 2910618 3420978 4077619 2714786 2844051 2778514 2843537 2712207 2777229 2711434 2645127 2579075 1789559 252 252 252 252 252 252 
252 252 252 252 252 252 15922679 2910359 2976661 3174301 3174816 3240868 3306918 3372713 3307434 3439022 3439024 3373745 3439282 3439282 3505075 3505075 2905975 2302755 2434341 3487029 3421236 3815994 2500134 12632256 9 11315880 3309242 3373231 3307181 3372716 3307179 3241387 3306665 3306664 3306923 3242418 3166315 3090466 3419432 3689048 2635072 3900089 3964337 4096695 3296353 3485999 3552822 3552822 3552822 3487029 3289650 5526612 10395294 13882323 9 9 9 9 12171705 3158064 4078650 3504302 3239324 3173274 3107480 3106966 3041174 2975380 2779290 3296354 3748654 4077363 2780063 2909844 2909844 2910875 1643279 2368548 4013373 3947580 4143154 2780577 2911133 2103314 2500134 2829099 4144959 4013373 2780320 2844566 2909846 2844309 2844567 2778259 2843794 2843536 2712207 2777485 2711691 2579849 2579076 2513025 4155529 252 252 252 252 252 252 
252 252 252 252 252 252 252 6458283 2909845 2976665 3042714 3109023 3175076 3240869 3241128 3306923 3372717 3307437 3307694 3373231 3438767 3439797 2102797 2302755 3421236 4079166 4144959 2697513 2763306 2829099 11447982 9 12105653 3566228 3241386 3306409 3241128 3240616 3175078 3175078 3240356 3240099 3174306 3240099 3437478 3437735 3634601 3831979 3963565 4029871 4424115 4555958 5017283 2762790 3552307 3552822 3552822 3552822 3289650 6776679 11382189 9 9 9 9 9 11777720 3501981 3238551 3238294 3106708 2975379 2975122 2909329 2777999 2843280 2843537 2778257 2843537 2844051 2778259 2844052 2843793 4079166 3947837 4079166 2780063 2910101 2910102 2910102 2769492 4276029 4143670 4273709 2909588 2909844 2844052 2778515 2843538 2843793 2712464 2777486 2646156 2711434 2579848 2513797 2447231 671593 252 252 252 252 252 252 252 
252 252 252 252 252 252 252 252 1989002 2976151 2976664 3042973 3109026 3174819 3175077 3306665 3306922 3306923 3307180 3372716 3372973 3307437 3441343 2433052 4144959 4144959 4079166 2631720 2763306 5658198 9 9 9 11908533 8027519 3044008 3240614 3240614 3174820 3174564 3174307 3174305 3108512 3239841 3371427 3503013 3634342 3831721 3963306 4029356 4358321 4621492 5015994 5608131 6268122 3160385 3552822 3552822 2434341 9211020 11842740 9 12434877 9 9 9 8752016 3633051 3172501 3106708 3106450 2974865 2909072 2843278 2777743 2712207 2777999 2777744 2843537 2843793 2843794 2843794 2778515 3233395 3233912 3818572 2909844 2909844 2909844 2909844 2909844 2779806 2844568 2844052 2778515 2844051 2843794 2843793 2778000 2712207 2777486 2646156 2711434 2579848 2513797 2513282 2381180 14344935 252 252 252 252 252 252 252 
252 252 252 252 252 252 252 252 9481410 2844051 2975895 2976920 3042975 3174305 3109028 3240614 3175079 3241128 3306666 3241386 3241386 3241387 3241387 2975121 4209205 4143928 3563392 2630689 2697513 12566463 9 9 9 9 9 11248026 3238809 3043493 3174306 3174049 3174048 3108511 3107998 3108255 3371169 3502498 3634340 3831462 3962792 4094634 4489135 4884149 5278651 5804995 6134215 6463181 6265803 2434083 7368816 11776947 9 12566463 2894892 5723991 11974326 12566205 3634341 3435159 3106450 3040657 3040656 2843278 2843277 2711692 2777229 2777741 2777742 2777486 2712464 2777743 2843536 2843792 2843794 2843537 2843794 2844050 2778258 2778514 2778514 2778514 2778514 2778515 2844051 2843537 2843793 2843793 2843537 2712463 2777742 2777229 2645899 2711178 2580104 2579334 2513282 2381695 342628 252 252 252 252 252 252 252 252 
252 252 252 252 252 252 252 252 252 2054278 2778001 2844564 3041947 3042461 3108255 3108513 3174306 3109028 3174821 3240358 3175078 3175335 3175079 3175079 3175079 3175079 3175079 3240872 3100779 2434341 10658466 9 11842740 10329501 1776411 12566463 9 11974325 5929103 2255007 2911134 3042204 3041947 3042203 3239325 3436447 3633568 3765410 3962276 4028069 4554669 4949427 5278392 5870271 6199495 6067392 9341059 11776947 9 9 12105912 3092271 3552822 3750201 3881787 3425878 3434899 3237777 3105678 2974349 2843020 2842506 2776970 2776971 2646155 2645899 2646156 2777229 2777230 2777742 2777486 2777743 2712464 2712463 2777744 2777744 2843537 2843537 2843537 2843537 2778001 2843280 2712463 2712464 2712207 2777487 2777742 2711692 2645899 2711178 2579848 2645383 2513797 2447745 2381694 2315129 252 252 252 252 252 252 252 252 252 
252 252 252 252 252 252 252 252 252 10138309 2711435 2843537 2910102 2910617 3041947 3042462 3042719 3108513 3174306 3108771 3109028 3174820 3174820 3174820 3174821 3174821 3174821 3174820 1975594 3158064 3092271 4408131 3158064 3750201 3289650 3026478 7566195 9 11711155 11908276 11446434 4941694 2188956 2910618 3239067 3370397 3502238 3699103 3764895 3830688 4422569 4752048 5015736 5209506 8091507 11119017 9 9 9 9 9 12763842 3684408 3815994 3881787 3633053 3434641 3171727 2974348 2843019 2777226 2711178 2776713 2645641 2711178 2711435 2711691 2645900 2646156 2711948 2777230 2777485 2777742 2777487 2777486 2777486 2712207 2712207 2712207 2711951 2777486 2777487 2777487 2777742 2777229 2711949 2646156 2711435 2645642 2580104 2645127 2513796 2447746 2447231 2380665 1262954 252 252 252 252 252 252 252 252 252 
252 252 252 252 252 252 252 252 252 252 7903152 2645642 2777999 2778258 2844309 2910616 2976410 2976668 3042462 3108255 3042719 3042976 3175078 3306922 3306923 3306923 3174820 2976926 3158064 3092271 3158064 4144959 3815994 3289650 3421236 3552822 3421236 9 9 9 9 11776947 9 11842741 12039861 11842225 11513001 11051677 10525334 11248800 11974068 11908533 11842740 9 9 11974326 7303023 2368548 13158600 9 9 9 4209979 3815737 3950158 3434384 3237262 3105675 2908040 2842247 2710920 2776455 2645384 2711175 2580104 2579849 2645641 2711434 2711178 2711435 2711435 2645899 2645899 2646156 2646157 2711948 2711693 2711949 2711949 2711949 2711949 2711693 2645900 2646155 2711435 2711434 2645641 2645384 2645127 2513797 2513282 2513024 2381438 2315128 210528 252 252 252 252 252 252 252 252 252 252 
252 252 252 252 252 252 252 252 252 252 252 1067124 2711691 2711950 2843793 2909845 2910103 2910616 2976410 3042204 2976668 3042461 1058360 2778001 2976410 250 3240358 3108512 3089951 3158064 3289650 4013373 3748396 3289650 3355443 3158064 3618615 9 9 9 11842740 3487029 7697781 11119017 9 9 9 9 9 9 9 9 9 9 9 8487297 4013373 2368548 2829099 12698049 9 10197915 4225190 3830173 3697556 3368590 3236747 3039625 2841990 2710918 2776454 2645382 2645126 2579590 2645127 2645127 2645384 2580104 2579848 2645641 2711434 2711178 2711434 2711435 2711435 2711691 2711691 2711691 2711691 2711691 2711435 2711435 2711178 2645641 2579849 2579848 2645383 2579590 2579332 2513539 2513024 2446974 2315386 1854064 252 252 252 252 252 252 252 252 252 252 252 
252 252 252 252 252 252 252 252 252 252 252 252 2579589 2711434 2777485 2843793 2844052 2844309 2975896 2976153 2910617 2976410 3174563 3041947 3439025 198154 3042204 3042204 3042979 3222568 4144701 3947323 2910876 2911135 3551017 1579032 1447446 8355711 11974326 9 11184810 3881787 3881787 4013373 11908533 9 9 9 7434609 4539717 4671303 8421504 9 9 9 12369084 3815994 2894892 3158064 3223857 4210752 3815735 4025747 3762576 3631247 3302538 3104905 2841989 2776196 2710404 2710660 2644868 2579332 2513540 2514053 2579589 2645126 2645127 2645127 2645384 2580104 2580104 2579849 2645642 2645897 2645897 2711434 2711434 2711177 2645641 2645641 2579849 2580104 2645384 2645127 2645126 2514054 2579075 2447746 2513024 2446973 2380923 2314615 11452106 252 252 252 252 252 252 252 252 252 252 252 
252 252 252 252 252 252 252 252 252 252 252 252 7377064 2447488 2579591 2646155 2777486 2778000 2778258 2844052 2909844 2909846 2844566 2910103 3372460 198154 2910360 2910359 2910359 2910103 2910103 2910102 2844310 2909845 2909845 1579031 3750201 3684408 3750201 3487029 3881787 3815994 3947580 1710618 10263708 9 9 9 5723991 4144959 2697513 2302755 7039851 9 9 12105912 2434341 3092271 3289650 3552822 3881787 3560557 3564938 3367303 3170181 2841474 2644352 2644352 2578817 2578817 2513281 2513281 2447489 2513282 2578819 2579075 2579332 2579076 2513797 2514054 2645126 2645126 2645382 2645383 2645383 2645127 2645127 2645383 2645127 2645382 2579590 2579590 2514053 2513797 2579076 2578819 2447746 2447231 2381438 2446717 2314872 2248821 12633 252 252 252 252 252 252 252 252 252 252 252 252 
252 252 252 252 252 252 252 252 252 252 252 252 252 1263215 2447231 2579590 2580105 2646155 2777486 2712208 2843537 2778258 2844051 2844052 3240872 132617 2909845 2909845 2909844 2909844 2909844 2844052 2778259 2778258 2844310 2697513 3684408 3618615 3750201 3617327 3881271 3947580 3947580 1710618 986895 12171705 12763842 12829635 3158064 4144959 1776411 2368548 2631720 8618883 4737096 3486254 3428454 3223342 3355443 3947580 3881272 3367818 3235973 2972802 2841216 2578557 2644093 2578558 2578559 2447231 2512767 2513024 2512768 2513025 2447490 2447490 2448002 2578818 2579076 2579332 2579332 2513797 2513796 2514053 2514053 2514054 2514054 2514053 2513797 2513541 2579333 2579332 2579075 2513539 2447489 2513025 2381695 2446973 2315387 2315129 2183028 1262183 252 252 252 252 252 252 252 252 252 252 252 252 252 
252 252 252 252 252 252 252 252 252 252 252 252 252 252 737129 2447232 2513540 2579590 2645898 2645900 2711949 2711951 2777744 2778000 1917794 250 2711691 2843537 2843794 2843537 2843537 2778000 2778000 2777744 2712207 3815737 3684408 3684408 3947323 2581139 2580881 2840443 1973791 1710618 2894892 4013373 3750201 3618356 4209979 4341821 2171169 2565927 2697513 4144959 4013373 3621967 3235715 3105161 3420977 3297641 3038336 3038336 2906751 2709372 2512250 2577787 2512508 2512508 2446972 2446716 2381181 2381438 2446974 2447231 2512768 2513024 2513024 2447489 2447746 2513282 2513283 2513283 2579075 2579075 2579075 2579075 2579075 2579075 2513283 2513283 2513538 2447746 2447489 2513024 2447231 2381438 2381180 2380665 2249336 2248820 1919340 252 252 252 252 252 252 252 252 252 252 252 252 252 252 
252 252 252 252 252 252 252 252 252 252 252 252 252 252 252 1788785 2380923 2447231 2513283 2579333 2579847 2645641 2645642 2645899 2711692 2711692 2711692 2711692 2711692 2711692 2711692 2711693 2646155 2645899 2645898 2645899 2515603 3100005 2515344 2579591 2579334 2513540 2513024 1842204 4079166 4013373 4079166 2382470 2512509 2446716 2433052 2697513 3618615 4013373 4274998 2643578 2643063 2643063 2643063 2643064 2577528 2577528 2445942 2446199 2446199 2380664 2446200 2380665 2315129 2315130 2380922 2380923 2381180 2446716 2446973 2381438 2381438 2381438 2447231 2447231 2512768 2513024 2513024 2513024 2513024 2513025 2513024 2513024 2512768 2447231 2447231 2381438 2446973 2381180 2315387 2380665 2314871 2248820 2182770 2116461 252 252 252 252 252 252 252 252 252 252 252 252 252 252 252 
252 252 252 252 252 252 252 252 252 252 252 252 252 252 252 13358556 2117492 2315129 2446974 2513025 2513539 2579333 2645126 2645383 2579848 2645641 2645641 2645641 2645898 2711178 2645642 2645641 2645641 2579848 2579848 2645127 2645127 2579590 2513797 2579332 2513283 2447745 2513539 1708556 4013373 3947580 4144445 2446715 2380922 2446201 2380923 2762017 4210495 4078908 2706279 2577013 2511477 2511477 2445685 2445685 2445941 2445685 2445686 2445686 2445687 2314871 2380408 2380407 2380407 2380408 2380409 2380666 2380666 2315387 2381179 2381180 2446716 2446973 2446973 2446974 2381694 2381694 2381438 2381438 2447231 2447231 2381695 2381438 2381438 2446973 2446973 2381180 2315387 2380666 2315128 2314614 2183028 2182513 2050669 3036017 252 252 252 252 252 252 252 252 252 252 252 252 252 252 252 
252 252 252 252 252 252 252 252 252 252 252 252 252 252 252 252 13161178 2117233 2315130 2381181 2381694 2447490 2513283 2579076 2513797 2513797 2579590 2579590 2579590 2645127 2579590 2579590 2579334 2513797 2513797 2579076 2579076 2513539 2447746 2513025 2512768 2447231 2381438 2447232 3360597 3491153 3620677 2380408 2380407 2314614 2314357 2380664 2249080 2380148 2380147 2445428 2445428 2445428 2445684 2380148 2380148 2379892 2379893 2314357 2379894 2249078 2249078 2248822 2314614 2249079 2249335 2249336 2315128 2380665 2380921 2380666 2380923 2315643 2381179 2381180 2446717 2446973 2446972 2446973 2446973 2446973 2446716 2381180 2315643 2315387 2315387 2380665 2314872 2249335 2248821 2248563 2116977 2116204 2707053 252 252 252 252 252 252 252 252 252 252 252 252 252 252 252 252 
252 252 252 252 252 252 252 252 252 252 252 252 252 252 252 252 252 252 2050669 2183027 2249078 2380666 2380924 2446717 2447230 2447231 2513024 2513025 2447745 2513281 2447745 2447489 2513025 2513024 2513025 2447232 2447231 2447230 2446973 2446716 2381179 2380922 2380665 2315128 2249079 2314614 2248820 2248563 2248306 2248305 2248304 2248305 2248562 2313842 2314098 2314099 2314099 2248563 2248563 2248563 2248563 2248562 2314355 2248820 2183284 2183027 2183027 2183027 2183027 2183284 2248820 2248821 2314614 2314614 2314871 2249336 2249336 2314873 2380409 2380922 2380665 2380665 2380665 2380665 2380665 2380665 2315129 2315128 2314872 2249335 2314615 2248821 2248563 2248306 2182512 2116461 2050410 252 252 252 252 252 252 252 252 252 252 252 252 252 252 252 252 252 252 
252 252 252 252 252 252 252 252 252 252 252 252 252 252 252 252 252 252 13095385 1984618 2116719 2183027 2314614 2314872 2380665 2315387 2381179 2446973 2381437 2381438 2381437 2381437 2446973 2446973 2446973 2446716 2381180 2315387 2380922 2380665 2315128 2249079 2314614 2248821 2183028 2183026 2182769 2117232 2116721 2116720 2116721 2116977 2182512 2182512 2182513 2182770 2182770 2182770 2182770 2182770 2182770 2182769 2183026 2248306 2248305 2248049 2182513 2182513 2182514 2248306 2248307 2248563 2183028 2183028 2314614 2314358 2314615 2314616 2249335 2249079 2249079 2249079 2249079 2249079 2249079 2249335 2314614 2314614 2314614 2248820 2183027 2182769 2116976 2182255 2050410 1984359 2641259 252 252 252 252 252 252 252 252 252 252 252 252 252 252 252 252 252 252 
252 252 252 252 252 252 252 252 252 252 252 252 252 252 252 252 252 252 252 13423835 1721188 2116461 2116976 2182770 2248821 2249078 2249335 2315129 2315129 2315129 2380666 2380666 2380666 2315129 2380665 2380665 2314872 2249335 2249078 2314614 2248821 2183028 2183027 2248306 2248562 2248050 2117234 2182769 2182257 2182257 2182769 2182769 2182769 2248305 2248305 2248304 2248304 2248304 2182768 2117232 2117232 2117232 2116976 2117232 2116976 2116720 2182256 2182255 2182768 2117234 2248563 2248564 2248820 2248820 2183028 2248820 2314614 2314614 2314357 2248821 2248821 2248821 2248821 2248821 2248821 2248820 2183028 2183028 2248306 2182513 2116976 2116462 2050926 2050410 1918309 2641258 252 252 252 252 252 252 252 252 252 252 252 252 252 252 252 252 252 252 252 
252 252 252 252 252 252 252 252 252 252 252 252 252 252 252 252 252 252 252 252 252 734551 1984103 2050153 2116461 2182255 2116976 2248307 2248563 2248821 2183028 2183028 2183028 2183028 2183028 2183028 2183028 2183284 2183284 2248564 2248562 2182513 2182513 2182513 2182513 2182514 2117234 2182769 2182769 2182769 2182769 2182769 2182769 2117233 2248306 2248306 2182770 2117234 2182770 2182769 2182769 2182769 2182769 2182769 2182769 2182769 2182257 2182257 2117234 2248562 2248562 2248306 2248563 2248562 2248562 2248563 2248307 2248306 2182770 2182513 2182513 2182513 2248305 2248563 2182770 2117233 2116976 2182255 2116462 2050668 2116204 2050410 1918566 1720673 252 252 252 252 252 252 252 252 252 252 252 252 252 252 252 252 252 252 252 252 252 
252 252 252 252 252 252 252 252 252 252 252 252 252 252 252 252 252 252 252 252 252 252 9802 1918566 1984618 2050411 2050926 2116719 2182513 2116976 2182513 2182769 2182513 2116977 2116977 2182513 2182513 2182513 2182769 2182769 2117233 2182512 2182512 2182512 2182512 2182513 2182513 2182769 2182769 2182769 2182768 2182768 2182769 2182770 2248306 2182770 2182770 2182770 2182770 2182770 2117234 2182770 2182770 2182768 2182768 2182769 2182769 2182769 2182513 2248563 2248306 2182769 2182769 2117233 2182514 2182769 2116977 2182512 2182256 2182255 2182513 2182769 2182514 2116976 2182255 2182255 2116462 2050668 2116203 2050411 2050411 1983845 1063258 252 252 252 252 252 252 252 252 252 252 252 252 252 252 252 252 252 252 252 252 252 252 
252 252 252 252 252 252 252 252 252 252 252 252 252 252 252 252 252 252 252 252 252 252 252 4285308 1918823 2049896 1984618 2116204 2050669 2116719 2181999 2116462 2116718 2116462 2116462 2182511 2182513 2182511 2182255 2182255 2182255 2182512 2182512 2182512 2182513 2182513 2182513 2182769 2182769 2182768 2182770 2182770 2182770 2182770 2117234 2117234 2117234 2182770 2182770 2182770 2248306 2117234 2182770 2182770 2182770 2182768 2182769 2182768 2117234 2117233 2117232 2182512 2182256 2182255 2182255 2182255 2182511 2182512 2182512 2182512 2182257 2182513 2182511 2116462 2050669 2050668 2115947 2116204 1984873 2050153 1918310 10572 252 252 252 252 252 252 252 252 252 252 252 252 252 252 252 252 252 252 252 252 252 252 252 
252 252 252 252 252 252 252 252 252 252 252 252 252 252 252 252 252 252 252 252 252 252 252 252 252 537173 1918822 2050153 1984873 2116203 2115948 2116204 2115947 2116461 2116460 2116205 2051181 2116462 2182255 2182512 2182512 2182512 2182512 2182511 2182257 2182769 2182769 2182768 2182770 2182770 2182770 2182770 2117234 2248306 2248306 2248306 2248306 2248306 2248306 2248306 2248306 2248306 2117234 2182770 2182770 2182770 2182770 2182768 2182769 2182769 2182257 2182511 2182512 2182512 2182512 2182512 2182512 2182255 2182255 2182512 2116462 2050925 2116204 2115946 2116204 2116204 1984874 2050152 1918310 1523551 9281969 252 252 252 252 252 252 252 252 252 252 252 252 252 252 252 252 252 252 252 252 252 252 252 252 
252 252 252 252 252 252 252 252 252 252 252 252 252 252 252 252 252 252 252 252 252 252 252 252 252 252 1589345 1918566 2050152 1984617 1984618 1984618 2116204 2115947 2116461 2116462 2116718 2116717 2182255 2181998 2182512 2182512 2182512 2182512 2182257 2182769 2182769 2182770 2182770 2182770 2117234 2248306 2248306 2248050 2248306 2248306 2248306 2248306 2248306 2248306 2248306 2248306 2248306 2117234 2182770 2182770 2182770 2182770 2182769 2182769 2182257 2182513 2182512 2182512 2182512 2182512 2182255 2182255 2116719 2050925 2116204 2115947 2116204 2116202 2116203 1984874 2049895 1918567 77136 252 252 252 252 252 252 252 252 252 252 252 252 252 252 252 252 252 252 252 252 252 252 252 252 252 252 
252 252 252 252 252 252 252 252 252 252 252 252 252 252 252 252 252 252 252 252 252 252 252 252 252 252 252 4087674 1852773 2050152 2050153 2050410 2116203 2116203 2116461 2116460 2116206 2116717 2182255 2181998 2182512 2182512 2182512 2182513 2182769 2182769 2182769 2182770 2182770 2182770 2182770 2248306 2248050 2248562 2248562 2248561 2248562 2248562 2248562 2248562 2248561 2248562 2248306 2248306 2182770 2182770 2182770 2182770 2182769 2182769 2182769 2182513 2182511 2182512 2182512 2181998 2182255 2051182 2116461 2116460 2116461 2116204 2116204 2050411 1984617 2050152 1918566 10317 252 252 252 252 252 252 252 252 252 252 252 252 252 252 252 252 252 252 252 252 252 252 252 252 252 252 252 
252 252 252 252 252 252 252 252 252 252 252 252 252 252 252 252 252 252 252 252 252 252 252 252 252 252 252 252 252 3298931 1852517 2049896 1984618 2116202 2116204 2116461 2116462 2116718 2116719 2182255 2182255 2182512 2182512 2182511 2182257 2182769 2182769 2182770 2182770 2182770 2248306 2248306 2248050 2248562 2248562 2248561 2248563 2248563 2248563 2248563 2248563 2248562 2248050 2248306 2248306 2117234 2182770 2182770 2182769 2182769 2182513 2182513 2182512 2182512 2181998 2182255 2116719 2116462 2116461 2116461 2116203 2116203 1984618 2049896 2049639 143444 252 252 252 252 252 252 252 252 252 252 252 252 252 252 252 252 252 252 252 252 252 252 252 252 252 252 252 252 252 
252 252 252 252 252 252 252 252 252 252 252 252 252 252 252 252 252 252 252 252 252 252 252 252 252 252 252 252 252 252 252 1326432 2050153 1984618 2116203 2116205 2116460 2116206 2116717 2182255 2182255 2182512 2182512 2182511 2182257 2182769 2182769 2182769 2182770 2182770 2248306 2248306 2248562 2248562 2248562 2248562 2248562 2248563 2248563 2248563 2248561 2248562 2248306 2248306 2248306 2182770 2182770 2182769 2182769 2182769 2182257 2182511 2182512 2182512 2182255 2182255 2051182 2116206 2116461 2115948 2116203 1984619 2050153 274773 14278628 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 10005433 800860 1984874 2116204 2115948 2116460 2116206 2051181 2182255 2181998 2182512 2182512 2182513 2182257 2182769 2182769 2182769 2182770 2117234 2248306 2248050 2248306 2248562 2248562 2248562 2248561 2248563 2248561 2248562 2248306 2248306 2182770 2182770 2182770 2182770 2182769 2182769 2182257 2182513 2182512 2182512 2181998 2182255 2051181 2116462 2116460 2115947 2116203 1984874 1524324 3825273 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 5008518 1064288 2116202 2116204 2116460 2116206 2116719 2181998 2182512 2182512 2182511 2182512 2182513 2182769 2182768 2182770 2182770 2117234 2117234 2117234 2182770 2248050 2248050 2248050 2248050 2182770 2117234 2117234 2182770 2182770 2182768 2182769 2182513 2182256 2182511 2182512 2181998 2181998 2051182 2116206 2116460 2116461 2116203 1590118 1392481 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 12371921 1064289 2050411 2116204 2116462 2051182 2116718 2182255 2182512 2182512 2182512 2182257 2182513 2182768 2182769 2182769 2182770 2182770 2182770 2117234 2117234 2117234 2182770 2182770 2182769 2182769 2182768 2182768 2182513 2182256 2182512 2182512 2182512 2182255 2116719 2051182 2116462 2116205 2115947 1392739 8295848 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 16645629 4153983 1458790 2116204 2116205 2051182 2181999 2181998 2182512 2182511 2182512 2182257 2182513 2182513 2182768 2182768 2182768 2182769 2182769 2182769 2182768 2182768 2182769 2182769 2182513 2182257 2182511 2182512 2182512 2182255 2181998 2116718 2116205 2116460 1721704 1392739 12635092 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 252 252 252 252 252 7441312 1590119 1064546 1919340 2116718 2116719 2181998 2182255 2182255 2182512 2182511 2182511 2182511 2182511 2182511 2182511 2182512 2182512 2182512 2182255 2181998 2116718 2116718 2050926 1130339 603997 7178398 252 252 252 252 252 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 252 252 252 252 252 252 252 252 252 10925506 5336970 209497 801632 1196133 1393511 1919340 1919340 1919340 1919340 1919340 1919341 1919340 1590633 1327718 801632 341596 5797777 11320520 252 252 252 252 252 252 252 252 252 252 252 252 252 252 252 252 252 252 252 252 252 252 252 252 252 252 252 252 252 252 252 252 252 252 252 252 252 252 252 252 252 252 252 252 252 252 252 252 
252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 252 

     )
)
(defun get-hard-drive-serial-number (drive-letter / serial)
  (setq serial "")
  (if (setq vol (vlax-get-or-create-object "Scripting.FileSystemObject"))
    (if (setq drive (vlax-invoke-method vol 'GetDrive drive-letter))
      (setq serial (vlax-get-property drive 'SerialNumber))
    )
    (princ "Erro: Não foi possível criar o objeto Scripting.FileSystemObject.")
  )
  serial
)
(defun programa_principal()
	(setvar "cmdecho" 0)
	(setq licencaativa 0)
	(setq num_serial (itoa (get-hard-drive-serial-number "C")))
	(setq comprimento_str (strlen num_serial))
	(setq pos_str 1)
	(setq codigo_gerado 0)
	(while (<= pos_str comprimento_str)
		(setq char_pos_atual (substr num_serial pos_str 1))
		(cond
			(
				(= char_pos_atual " ") 
				(setq codigo_gerado (+ codigo_gerado 32))
			)
			(
				(= char_pos_atual "!") 
				(setq codigo_gerado (+ codigo_gerado 33))
			)
			(
				(= char_pos_atual "\"") 
				(setq codigo_gerado (+ codigo_gerado 34))
			)
			(
				(= char_pos_atual "#") 
				(setq codigo_gerado (+ codigo_gerado 35))
			)
			(
				(= char_pos_atual "$") 
				(setq codigo_gerado (+ codigo_gerado 36))
			)
			(
				(= char_pos_atual "%") 
				(setq codigo_gerado (+ codigo_gerado 37))
			)
			(
				(= char_pos_atual "&") 
				(setq codigo_gerado (+ codigo_gerado 38))
			)
			(
				(= char_pos_atual "'") 
				(setq codigo_gerado (+ codigo_gerado 39))
			)
			(
				(= char_pos_atual "(") 
				(setq codigo_gerado (+ codigo_gerado 40))
			)
			(
				(= char_pos_atual ")")
				(setq codigo_gerado (+ codigo_gerado 41))
			)
			(
				(= char_pos_atual ")")
				(setq codigo_gerado (+ codigo_gerado 41))
			)
			(
				(= char_pos_atual "*")
				(setq codigo_gerado (+ codigo_gerado 42))
			)
			(
				(= char_pos_atual "+")
				(setq codigo_gerado (+ codigo_gerado 43))
			)
			(
				(= char_pos_atual ",")
				(setq codigo_gerado (+ codigo_gerado 44))
			)
			(
				(= char_pos_atual "-")
				(setq codigo_gerado (+ codigo_gerado 45))
			)
			(
				(= char_pos_atual ".")
				(setq codigo_gerado (+ codigo_gerado 46))
			)
			(
				(= char_pos_atual "/")
				(setq codigo_gerado (+ codigo_gerado 47))
			)
			(
				(= char_pos_atual "0")
				(setq codigo_gerado (+ codigo_gerado 48))
			)
			(
				(= char_pos_atual "1")
				(setq codigo_gerado (+ codigo_gerado 49))
			)
			(
				(= char_pos_atual "2")
				(setq codigo_gerado (+ codigo_gerado 50))
			)
			(
				(= char_pos_atual "3")
				(setq codigo_gerado (+ codigo_gerado 51))
			)
			(
				(= char_pos_atual "4")
				(setq codigo_gerado (+ codigo_gerado 52))
			)
			(
				(= char_pos_atual "5")
				(setq codigo_gerado (+ codigo_gerado 53))
			)
			(
				(= char_pos_atual "6")
				(setq codigo_gerado (+ codigo_gerado 54))
			)
			(
				(= char_pos_atual "7")
				(setq codigo_gerado (+ codigo_gerado 55))
			)
			(
				(= char_pos_atual "8")
				(setq codigo_gerado (+ codigo_gerado 56))
			)
			(
				(= char_pos_atual "9")
				(setq codigo_gerado (+ codigo_gerado 57))
			)
			(
				(= char_pos_atual ":")
				(setq codigo_gerado (+ codigo_gerado 58))
			)
			(
				(= char_pos_atual ";")
				(setq codigo_gerado (+ codigo_gerado 59))
			)
			(
				(= char_pos_atual "<")
				(setq codigo_gerado (+ codigo_gerado 60))
			)
			(
				(= char_pos_atual "=")
				(setq codigo_gerado (+ codigo_gerado 61))
			)
			(
				(= char_pos_atual ">")
				(setq codigo_gerado (+ codigo_gerado 62))
			)
			(
				(= char_pos_atual "?")
				(setq codigo_gerado (+ codigo_gerado 63))
			)
			(
				(= char_pos_atual "@")
				(setq codigo_gerado (+ codigo_gerado 64))
			)
			(
				(= char_pos_atual "A")
				(setq codigo_gerado (+ codigo_gerado 65))
			)
			(
				(= char_pos_atual "B")
				(setq codigo_gerado (+ codigo_gerado 66))
			)
			(
				(= char_pos_atual "C")
				(setq codigo_gerado (+ codigo_gerado 67))
			)
			(
				(= char_pos_atual "D")
				(setq codigo_gerado (+ codigo_gerado 68))
			)
			(
				(= char_pos_atual "E") 
				(setq codigo_gerado (+ codigo_gerado 69))
			)
			(
				(= char_pos_atual "F")
				(setq codigo_gerado (+ codigo_gerado 70))
			)
			(
				(= char_pos_atual "G")
				(setq codigo_gerado (+ codigo_gerado 71))
			)
			(
				(= char_pos_atual "H")
				(setq codigo_gerado (+ codigo_gerado 72))
			)
			(
				(= char_pos_atual "I")
				(setq codigo_gerado (+ codigo_gerado 73))
			)
			(
				(= char_pos_atual "J")
				(setq codigo_gerado (+ codigo_gerado 74))
			)
			(
				(= char_pos_atual "K")
				(setq codigo_gerado (+ codigo_gerado 75))
			)
			(
				(= char_pos_atual "L")
				(setq codigo_gerado (+ codigo_gerado 76))
			)
			(
				(= char_pos_atual "M")
				(setq codigo_gerado (+ codigo_gerado 77))
			)
			(
				(= char_pos_atual "N")
				(setq codigo_gerado (+ codigo_gerado 78))
			)
			(
				(= char_pos_atual "O")
				(setq codigo_gerado (+ codigo_gerado 79))
			)
			(
				(= char_pos_atual "P")
				(setq codigo_gerado (+ codigo_gerado 80))
			)
			(
				(= char_pos_atual "Q")
				(setq codigo_gerado (+ codigo_gerado 81))
			)
			(
				(= char_pos_atual "R")
				(setq codigo_gerado (+ codigo_gerado 82))
			)
			(
				(= char_pos_atual "S")
				(setq codigo_gerado (+ codigo_gerado 83))
			)
			(
				(= char_pos_atual "T")
				(setq codigo_gerado (+ codigo_gerado 84))
			)
			(
				(= char_pos_atual "U")
				(setq codigo_gerado (+ codigo_gerado 85))
			)
			(
				(= char_pos_atual "V")
				(setq codigo_gerado (+ codigo_gerado 86))
			)
			(
				(= char_pos_atual "W")
				(setq codigo_gerado (+ codigo_gerado 87))
			)
			(
				(= char_pos_atual "X")
				(setq codigo_gerado (+ codigo_gerado 88))
			)
			(
				(= char_pos_atual "Y")
				(setq codigo_gerado (+ codigo_gerado 89))
			)
			(
				(= char_pos_atual "Z")
				(setq codigo_gerado (+ codigo_gerado 90))
			)
			(
				(= char_pos_atual "[")
				(setq codigo_gerado (+ codigo_gerado 91))
			)
			(
				(= char_pos_atual "\\")
				(setq codigo_gerado (+ codigo_gerado 92))
			)
			(
				(= char_pos_atual "]")
				(setq codigo_gerado (+ codigo_gerado 93))
			)
			(
				(= char_pos_atual "^")
				(setq codigo_gerado (+ codigo_gerado 94))
			)
			(
				(= char_pos_atual "_")
				(setq codigo_gerado (+ codigo_gerado 95))
			)
			(
				(= char_pos_atual "`") 
				(setq codigo_gerado (+ codigo_gerado 96))
			)
			(
				(= char_pos_atual "a")
				(setq codigo_gerado (+ codigo_gerado 97))
			)
			(
				(= char_pos_atual "b") 
				(setq codigo_gerado (+ codigo_gerado 98))
			)
			(
				(= char_pos_atual "c") 
				(setq codigo_gerado (+ codigo_gerado 99))
			)
			(
				(= char_pos_atual "d") 
				(setq codigo_gerado (+ codigo_gerado 100))
			)
			(
				(= char_pos_atual "e") 
				(setq codigo_gerado (+ codigo_gerado 101))
			)
			(
				(= char_pos_atual "f")
				(setq codigo_gerado (+ codigo_gerado 102))
			)
			(
				(= char_pos_atual "g")
				(setq codigo_gerado (+ codigo_gerado 103))
			)
			(
				(= char_pos_atual "h")
				(setq codigo_gerado (+ codigo_gerado 104))
			)
			(
				(= char_pos_atual "i") 
				(setq codigo_gerado (+ codigo_gerado 105))
			)
			(
				(= char_pos_atual "j")
				(setq codigo_gerado (+ codigo_gerado 106))
			)
			(
				(= char_pos_atual "k")
				(setq codigo_gerado (+ codigo_gerado 107))
			)
			(
				(= char_pos_atual "l")
				(setq codigo_gerado (+ codigo_gerado 108))
			)
			(
				(= char_pos_atual "m")
				(setq codigo_gerado (+ codigo_gerado 109))
			)
			(
				(= char_pos_atual "n") 
				(setq codigo_gerado (+ codigo_gerado 110))
			)
			(
				(= char_pos_atual "o") 
				(setq codigo_gerado (+ codigo_gerado 111))
			)
			(
				(= char_pos_atual "p")
				(setq codigo_gerado (+ codigo_gerado 112))
			)
			(
				(= char_pos_atual "q") 
				(setq codigo_gerado (+ codigo_gerado 113))
			)
			(
				(= char_pos_atual "r") 
				(setq codigo_gerado (+ codigo_gerado 114))
			)
			(
				(= char_pos_atual "s") 
				(setq codigo_gerado (+ codigo_gerado 115))
			)
			(
				(= char_pos_atual "t") 
				(setq codigo_gerado (+ codigo_gerado 116))
			)
			(
				(= char_pos_atual "u") 
				(setq codigo_gerado (+ codigo_gerado 117))
			)
			(
				(= char_pos_atual "v") 
				(setq codigo_gerado (+ codigo_gerado 118))
			)
			(
				(= char_pos_atual "w") 
				(setq codigo_gerado (+ codigo_gerado 119))
			)
			(
				(= char_pos_atual "x") 
				(setq codigo_gerado (+ codigo_gerado 120))
			)
			(
				(= char_pos_atual "y")
				(setq codigo_gerado (+ codigo_gerado 121))
			)
			(
				(= char_pos_atual "z") 
				(setq codigo_gerado (+ codigo_gerado 122))
			)
			(
				(= char_pos_atual "{") 
				(setq codigo_gerado (+ codigo_gerado 123))
			)
			(
				(= char_pos_atual "|") 
				(setq codigo_gerado (+ codigo_gerado 124))
			)
			(
				(= char_pos_atual "}") 
				(setq codigo_gerado (+ codigo_gerado 125))
			)
			(
				(= char_pos_atual "") 
				(setq codigo_gerado (+ codigo_gerado 126))
			)			
		)
		(setq pos_str (+ pos_str 1))
	)
	(setq codigo_gerado (* codigo_gerado 180277))
	(princ (strcat "teste" (itoa codigo_gerado) "\n"))
	(if (= (findfile "C:\\Program Files\\Autodesk\\AutoCAD 2023\\Support\\gpcnclsp.lic") nil)
		(progn
			(setq reply (acet-ui-message "A aplicação ainda não possui licença ativa.\nPossui o código de ativação? " "Ativar aplicação" (+ acet:YESNOCANCEL acet:ICONWARNING)))
			;; Yes = 6
			;; No = 7
			;; Cancel = 2
			(if (= reply 6)
				(progn 
					(setq codigo_recebido (getstring "\nDigite o serial para ativação do produto: "))
					(if (= (itoa codigo_gerado) codigo_recebido)
						(progn
							(setq fw (open "C:\\Program Files\\Autodesk\\AutoCAD 2023\\Support\\gpcnclsp.lic" "w"))
							(write-line (strcat num_serial "-" (itoa codigo_gerado)) fw)
							(close fw)
							(load "C:\\Program Files\\Autodesk\\AutoCAD 2023\\Support\\LSP\\Alpha_GPCNC_v5.lsp")
						)
						(progn
							(setq message_str (strcat "Serial não é válido"))
							(alert message_str)	
						)
					)
				)
				(progn
					(setq message_str (strcat "Envie o código " num_serial " para o endereço\n\nmauricio.nascimento@alphalsp.com.br\n\nNo máximo 24h lhe será enviada a chave de registro"))
					(alert message_str)	
				)
			)
		)
		(progn
			(setq fw (open "C:\\Program Files\\Autodesk\\AutoCAD 2023\\Support\\gpcnclsp.lic" "r"))
			(setq linha_procurada (strcat num_serial "-" (itoa codigo_gerado)))
			(princ linha_procurada)
			(setq linha_lida (read-line fw))
			(princ linha_lida)
			(close fw)
			(if (= linha_lida linha_procurada)
				(progn
					(setq licencaativa 1)
					(princ "\nAlpha Extrator de pontos para CNC\nDesenvolvido por AlphaLSP.\nComandos ZEROPECA, GTRAJ e GPCNC ")
					(defun listaentidades()
						(setq indice (+ 1 indice))
						(setq entidade (ssname entidades indice))
						(setq definicao (entget entidade))
						(setq tipo (cdr (assoc 0 definicao)))
					)
					(defun c:zeropeca()
						(setvar "cmdecho" 0)				
						(setq zp (getpoint "\nInforme o ponto \"ZERO\" da peça: "))
						(command "_move" "all" "" zp "0,0,0" (command))
						(command)
						;(entmake
						;	(list
						;		(cons 0 "CIRCLE")
						;		(cons 10 (list 100 0 0))
						;		(cons 40 1)
						;	)
						;)
						;(command)
						;(setq origem_ind_1 (ssget "_L"))
						(entmake
							(list
								(cons 0 "TEXT")
								(cons 1 "Z")
								(cons 10 (list 6 0 0))
								(cons 40 2)
								(cons 41 1)
								(cons 50 0)
								;(cons 72 4)
								;(cons 73 2)
							)
						)
						;(setq origem_ind_X (ssget "_L"))
						(entmake
							(list
								(cons 0 "TEXT")
								(cons 1 "X")
								(cons 10 (list 0 6 0))
								(cons 40 2)
								(cons 41 1)
								(cons 50 0)
								;(cons 72 1)
								;(cons 73 2)								
							)
						)
						;(setq origem_ind_Z (ssget "_L"))
						(command)
						(command "_circle" "100,0,0" "D" "2" (command))
						(setq origem_ind_1 (entlast))
						(command "_line" "100,3,0" "100,-1,0" (command))
						(setq origem_ind_2 (entlast))
						(command "_pline" "100,5" "99.5,3" "100.5,3" "100,5" ""(command))
						(setq origem_ind_3 (entlast))
						(command "_line" "99,0,0" "103,0,0" (command))
						(setq origem_ind_4 (entlast))
						(command "_pline" "105,0" "103,0.5" "103,-0.5" "105,0" "" (command))
						(setq origem_ind_5 (entlast))
						(command "_-bhatch" "properties" "solid" "99.5,0.5" "100.5,-0.5" "" (command))
						(setq origem_ind_6 (entlast))
						;(command "_block" "teste" "100,0,0" origem_ind_1 origem_ind_2 origem_ind_3 origem_ind_4 origem_ind_5 origem_ind_6 "")
						(command "_move" origem_ind_1 origem_ind_2 origem_ind_3 origem_ind_4 origem_ind_5 origem_ind_6 "" "100,0,0" "0,0,0" (command))
						(command)					
						(command "_zoom" "extents" (command))
						(setvar "cmdecho" 1)
					)
					(defun c:gtraj()
							(setvar "cmdecho" 0)
							(setq novo_layer "")
							(setq cor_traj "")
							(princ "\nSelecione o perfil para gerar a trajetória de usinagem:")
							(setq traj_usinagem (ssget))
							(setq novo_layer (getstring "\nInforme um nome para a trajetória (opcional):"))	
							(command "_copy" traj_usinagem "" "0,0,0" "0,0,0" (command))
							(command "_move" traj_usinagem "" "0,0,0" "0,100,0" (command))
							(princ "\nExecute o recorte do perfil onde necessário:")
							(command "_trim" "o" "q" "")
							(while
								(> (getvar "CMDACTIVE") 0)
								(command pause)
							)
							(command)
							(command "_pedit" "M" traj_usinagem "" "y" "j" "" (command))
							(setq traj_usinagem (entsel "\nSelecione a trajetória de finalizada: "))
							(if (/= novo_layer "")
								(progn
									(setq cor_traj (getint "\nInforme um valor de 1 à 255 para definir uma cor: "))
									(if (/= cor_traj "")
										(progn
											(command "layer" "n" novo_layer	"c" cor_traj novo_layer	(command))
										)
										(progn
											(command "layer" "n" novo_layer	"" (command))	
										)										
									)
									(command "_chprop" traj_usinagem "" "_LA" novo_layer "")
								)
							)
							(setq traj_usinagem_ext (vlax-ename->vla-object (car traj_usinagem))
							startpt (vlax-curve-getStartPoint traj_usinagem_ext)
							endpt (vlax-curve-getEndPoint traj_usinagem_ext))
							(command)
							(command "_circle" startpt "D" "5" (command))
							(setq ext_1 (entlast))
							(command "_circle" endpt "D" "5" (command))
							(setq ext_2 (entlast))
							(command "_extend" "" startpt endpt "")
							(command "_erase" ext_1 ext_2 "")
							(command "_move" traj_usinagem "" "0,100,0" "0,0,0" (command))
							(setvar "cmdecho" 1)

					)
					(defun c:gpcnc()
						(defun coordenada()
							(if (/= xatual nil)
								(progn
									(setq xanterior xatual)
								)
								(progn
									(setq xanterior (car ponto_partida))
								)
							)
							(if (/=  yatual nil)
								(progn
									(setq yanterior yatual)
								)
								(progn
									(setq yanterior (cadr ponto_partida))
								)
							)
							(setq xatual (cadr entidade))
							(setq yatual (caddr entidade))
							(setq cateto1 (- xatual xanterior))
							(setq cateto2 (- yatual yanterior))
							(setq bloco (strcat "X" (rtos (* yatual 2) 2 3) " Z" (rtos xatual 2 3)))
							(if (or (= comando "G2") (= comando "G3"))
								(progn
									(setq corda (/ (sqrt (+ (* cateto1 cateto1) (* cateto2 cateto2))) 2))
									(setq dif_ap_r (* corda tang))
									(setq raio_perfil (rtos (/ (+ (* corda corda) (* dif_ap_r dif_ap_r)) (* 2 dif_ap_r)) 2 3))
									(setq bloco (strcat bloco " R" raio_perfil))
								)
							)
						)
						(setq xatual nil)
						(setq yatual nil)
						(setq solicita_selecao 0)
						(defun slv (msg dir bit / err fld pth shl slf)
							(setq err
								(vl-catch-all-apply
									(function
										(lambda ( / app hwd )
											(if (setq app (vlax-get-acad-object)
													shl (vla-getinterfaceobject app "shell.application")
													hwd (vl-catch-all-apply 'vla-get-hwnd (list app))
													fld (vlax-invoke-method shl 'browseforfolder (if (vl-catch-all-error-p hwd) 0 hwd) msg bit dir)
												)
												(setq 
													slf (vlax-get-property fld 'self)
													pth (vlax-get-property slf 'path)
													pth (vl-string-right-trim "\\" (vl-string-translate "/" "\\" pth))
												)
											)
										)
									)
								)
							)
							(if slf (vlax-release-object slf))
							(if fld (vlax-release-object fld))
							(if shl (vlax-release-object shl))
							(if (vl-catch-all-error-p err)
							(prompt (vl-catch-all-error-message err))
								pth
							)
						)
						(defun parametros_inicio()
							(setq origem "")
							(if (= p1_ptw (itoa 1))
								(progn
									(setq origem "G54")
								)
								(progn
									(if (= p2_ptw (itoa 1))
										(progn
											(setq origem "G55")
										)
										(progn
											(if (= p3_ptw (itoa 1))
												(progn
													(setq origem "G56")
												)
												(progn
													(if (= p4_ptw (itoa 1))
														(setq origem "G57")
													)
												)
											)
										)
									)
								)
							)
							(setq param_2_str_ptw (strcat origem " G40"))
							(setq aprox_x (rtos (+ (atof mp_ptw) 5)))
							(if (= final_programa_ptw (itoa 1))
								(setq linha_final_ptw "M30")
								(setq linha_final_ptw "")
							)
						)
						(defun retem_valores()
							(setq programa_dir (get_tile "path_name_ptw"))
							(setq programa_ptw (get_tile "program_name_ptw"))
							(setq operacao_ptw (get_tile "operation_name_ptw"))
							(setq mp_ptw (get_tile "mp_diameter"))
							(setq p1_ptw (get_tile "p1"))
							(setq p2_ptw (get_tile "p2"))
							(setq p3_ptw (get_tile "p3"))
							(setq p4_ptw (get_tile "p4"))
						)
						(defun montar_programa()
							(retem_valores)
							(parametros_inicio)
							(setq final_programa_ptw (get_tile "program_end_ptw"))
							(princ final_programa_ptw)
							(setq solicita_selecao 1)
							(setq output_file (strcat programa_dir "\\" programa_ptw ".txt"))
							(done_dialog)
						)
						(defun cancela_tarefa()
							(retem_valores)
							(setq solicita_selecao 0)
							(done_dialog)
						)
						(setq solicita_selecao 0)
						(setq dcl-id (load_dialog "C:\\Program Files\\Autodesk\\AutoCAD 2023\\Support\\LSP\\cnc.dcl"))
					;	(setq file (vl-filename-mktemp "parametros.dcl"))
					;	(setq caixa_dialogo (open file "w"))
					;	(
					;		write-line 
					;		"PTW :dialog 
					;		{
					;			label=\"Extrair pontos para programa CNC\";
					;			:row
					;			{
					;				:column
					;				{
					;				}
					;				:column
					;				{
					;				}
					;				:column
					;				{
					;					:image_button
					;					{
					;						key=\"logo_image\";
					;						width=20;
					;						height=9.1;
					;						fixed_width=true;
					;						fixed_height=true;
					;					}
					;				}
					;				:column
					;				{
					;				}
					;			}
					;			:row
					;			{
					;				:boxed_row
					;				{
					;					label=\"Caminho do arquivo\";
					;					:edit_box
					;					{
					;						label=\"Pasta\";
					;						key=\"path_name_ptw\";
					;						width=50;
					;					}
					;					:button
					;					{
					;						label=\"Seleciona pasta\";
					;						key=\"select_button_ptw\";
					;					}
					;				}
					;			}
					;			:row
					;			{
					;				:boxed_column
					;				{
					;					label=\"Descritivo\";
					;					:edit_box
					;					{
					;						label=\"Nome do programa\";
					;						value=\"\";
					;						key=\"program_name_ptw\";
					;						width=50;
					;					}
					;					:edit_box
					;					{
					;						label=\"Nome da operação\";
					;						value=\"\";
					;						key=\"operation_name_ptw\";
					;						width=50;
					;					}
					;				}
					;			}
					;			:boxed_row
					;			{
					;				label=\"Origens\";
					;				:radio_button
					;				{
					;					label=\"G54\";
					;					value=1;
					;					key=\"p1\";
					;				}
					;				:radio_button
					;				{
					;					label=\"G55\";
					;					value=0;
					;					key=\"p2\";
					;				}
					;				:radio_button
					;				{
					;					label=\"G56\";
					;					value=0;
					;					key=\"p3\";
					;				}
					;				:radio_button
					;				{
					;					label=\"G57\";
					;					value=0;
					;					key=\"p4\";
					;				}
					;			}
					;			:boxed_row
					;			{
					;				label=\"Final do programa\";
					;				:radio_button
					;				{
					;					label=\"Nenhum\";
					;					value=1;
					;					key=\"continue_program_ptw\";
					;				}
					;				:radio_button
					;				{
					;					label=\"Fim de programa (M30)\";
					;					value=0;
					;					key=\"program_end_ptw\";
					;				}
					;			}
					;			:row
					;			{
					;				:button
					;				{
					;					label=\"OK\";
					;					key=\"ok_button_ptw\";
					;					action=\"(done_dialog 1)\";
					;					is_default = true;
					;				}
					;				:button
					;				{
					;					label=\"Cancela\";
					;					key=\"cancel_button_ptw\";
					;					action=\"(done_dialog 0)\";
					;					is_default = true;
					;				}
					;			}
					;		}"
					;		caixa_dialogo
					;	)
					;	(close caixa_dialogo)
					;	(setq dcl_id (load_dialog file))
						(if (not (new_dialog "PTW" dcl-id))
							(exit)
						)
						(DisplayBitmap "logo_image" test_blue)
						(if (/= programa_dir nil)
							(set_tile "path_name_ptw" programa_dir)
						)
						(if (/= programa_ptw nil)
							(set_tile "program_name_ptw" programa_ptw)
						)
						(if (/= operacao_ptw nil)
							(set_tile "operation_name_ptw" operacao_ptw)
						)
						(if (/= mp_ptw nil)
							(set_tile "mp_diameter" mp_ptw)
						)						
						(if (/= p1_ptw nil)
							(set_tile "p1" p1_ptw)
						)
						(if (/= p2_ptw nil)
							(set_tile "p2" p2_ptw)
						)
						(if (/= p3_ptw nil)
							(set_tile "p3" p3_ptw)
						)
						(if (/= p4_ptw nil)
							(set_tile "p4" p4_ptw )
						)
						(if (/= final_programa_ptw nil)
							(set_tile "program_end_ptw" final_programa_ptw)
						)
						(action_tile "select_button_ptw" "(set_tile \"path_name_ptw\" (slv \"Selecione a pasta de destino\" \"C:\" 0))")
						(action_tile "cancel_button_ptw" "(cancela_tarefa)")
						(action_tile "ok_button_ptw" "(montar_programa)")
						(start_dialog)
						(unload_dialog dcl-id)
						(if (= solicita_selecao 1)
							(progn
								(setvar "cmdecho" 1)
								(setq corpo_programa "")
								;(setq mp (getpoint "\nInforme o ponto de aproximacao da ferramenta: "))
								(setq ponto_partida (getpoint "\nInforme o ponto de inicio do perfil:"))
								(setq aproximacao (strcat "\n(CERTIFIQUE-SE DE QUE NÃO HÁ RISCO DE COLISÃO, NO MOMENTO DA ENTRADA, ANTES DE EXECUTAR O PROGRAMA NA MÁQUINA)\nG0 Z" (rtos (car ponto_partida) 2 3) ";\nG0 X" aprox_x ";"))
								(setq esz (strcat "\nG0 Z" (rtos (car ponto_partida) 2 3) ";"))
								(setq esx (strcat "\n(CERTIFIQUE-SE DE QUE NÃO HÁ RISCO DE COLISÃO, NO MOMENTO DA SAÍDA, ANTES DE EXECUTAR O PROGRAMA NA MÁQUINA)\nG1 X" aprox_x ";"))
								(setq perfil_usinagem (entsel "\nSelecione a trajetória de usinagem: "))
								(setq verificador_perfil_usinagem (vlax-ename->vla-object (car perfil_usinagem))
								startpt (vlax-curve-getStartPoint verificador_perfil_usinagem)
								endpt (vlax-curve-getEndPoint verificador_perfil_usinagem))	
								(if (and (/= (car startpt) (car ponto_partida)) (/= (cadr startpt) (cadr ponto_partida)))
									(progn
										(command "_pedit" "M" perfil_usinagem "" "r" "" (command))
									)
								)
								(setq perfil_usinagem (car perfil_usinagem))
								(setq selecao (entget perfil_usinagem))
								(while selecao
									(setq entidade (car selecao))
									(if (= (car entidade) 42)
										(progn
											(if (= (cdr entidade) 0)
												(progn
													(setq comando "G1")
												)	
												(progn
													(if (< (cdr entidade) 0)
														(progn
															(setq tang (* (cdr entidade) (- 0 1)))
															(setq comando "G2")
														)
														(progn
															(setq tang (cdr entidade))
															(setq comando "G3")
														)
													)
												)
											)
										)
										(progn
											(if (= (car entidade) 10)
												(progn
													(if (and (= (rtos (cadr entidade) 2 3) (rtos (car ponto_partida) 2 3)) (= (rtos (caddr entidade) 2 3) (rtos (cadr ponto_partida) 2 3)))
														(progn 
															(setq comando "G0")
															(coordenada)
															(setq bloco (strcat comando " " bloco ";"))
															(setq corpo_programa (strcat corpo_programa "\n" bloco))
														)
														(progn
															(coordenada)
															(setq bloco (strcat comando " " bloco ";"))
															(setq corpo_programa (strcat corpo_programa "\n" bloco))
														)
													)
												)
											)
										)
									)
									(setq selecao (cdr selecao))
								)
								(if (= (findfile output_file) nil)
									(progn
										(setq param_1_str_ptw "%0001\n")
										(setq corpo_programa (strcat param_1_str_ptw "(" operacao_ptw ")" "\n" param_2_str_ptw aproximacao corpo_programa esx esz "\n" linha_final_ptw ";"))
										(setq fw (open output_file "w"))
										(write-line corpo_programa fw)
										(close fw)
									)
									(progn
										(setq corpo_programa (strcat ";;;" "\n" "(" operacao_ptw ")" "\n" param_2_str_ptw aproximacao corpo_programa esx esz "\n" linha_final_ptw ";"))
										(setq fw (open output_file "a"))
										(write-line corpo_programa fw)
										(close fw)
									)
								)
							)
						)	
						(command)
					)					
				)
				(progn
					(vl-file-delete "C:\\Program Files\\Autodesk\\AutoCAD 2023\\Support\\gpcnclsp.lic")
					(setq message_str (strcat "Licença encontrada não válida\n\n\Envie o código " num_serial " para o endereço\n\nmauricio.nascimento@alphalsp.com.br\n\nNo máximo 24h lhe será enviada a chave de registro"))
					(alert message_str)
					(princ "")
				)
			)
		)
	)
	(setvar "cmdecho" 1)
)
(programa_principal)
(setvar "cmdecho" 1)
